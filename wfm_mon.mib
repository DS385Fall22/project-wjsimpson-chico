-- Machine generated MIB file!
-- DO NOT EDIT!
--
-- MIB file for MIB WFM-MIB, generated on Nov 20 2014 16:12:52 by snmpGlue
--
-- COPYRIGHT (c) TEKTRONIX, INC., 2009-2014
-- ALL RIGHTS RESERVED
-- 
-- TEKTRONIX, INC.
-- P.O. BOX 500
-- Beaverton OREGON 970777 U.S.A.
-- 
-- ===================================================================
--             T E K T R O N I X    C O N F I D E N T I A L
-- ===================================================================
-- 
-- This program is proprietary to TEKTRONIX, Inc. and is protected under
-- United States Copyright Law as an unpublished work. Its use and dis-
-- closure is limited by the terms and conditions of an express license
-- agreement. It may not be copied or otherwise reproduced or disclosed
-- to persons outside the licensee's organization except in accordance
-- with the terms and conditions of such agreement. All copies and re-
-- productions shall be the property of TEKTRONIX, Inc. and must bear
-- this notice in its entirety.
-- 
-- ===================================================================
-- 
--
-- DESCRIPTION:
-- contains SNMP OIDs common to waveform monitors.
-- 
-- This MIB uses
-- the SNMPv2 Structure of Management Information - SNMPv2-SMI (rfc 1902),
-- the SNMPv2 Textual Conventions - SNMPv2-TC (rfc 1903),
-- the SNMPv2 Conformance Statements - SNMPv2-CONF (rfc 1904).
-- 
-- 
-- Waveform monitors MIB
-- 

WFM-MIB DEFINITIONS ::= BEGIN

    IMPORTS
        MODULE-IDENTITY FROM SNMPv2-SMI
        OBJECT-TYPE FROM SNMPv2-SMI
        NOTIFICATION-TYPE FROM SNMPv2-SMI
        enterprises FROM SNMPv2-SMI
        DisplayString FROM SNMPv2-TC
        TEXTUAL-CONVENTION FROM SNMPv2-TC
    ;

wfm-mon         MODULE-IDENTITY
    LAST-UPDATED	"201411121200Z"
    ORGANIZATION	"Tektronix - Video Business Unit"
    CONTACT-INFO
		"Tektronix Inc.
		PO BOX 500
		Beaverton OR, 97077, USA
		http://www.tektronix.com
		+1 503-627-2400"
    DESCRIPTION 	"Common MIB for Tektronix video waveform monitors, Version 1.25"

    ::= { tvtmibs 10 }

tek             OBJECT IDENTIFIER ::= { enterprises 128 }

tvt             OBJECT IDENTIFIER ::= { tek 5 }

tvtproducts     OBJECT IDENTIFIER ::= { tvt 1 }

tvtmibs         OBJECT IDENTIFIER ::= { tvt 2 }

-- 
-- wfm-mon subgroups
gen             OBJECT IDENTIFIER ::= { wfm-mon 1 }

input           OBJECT IDENTIFIER ::= { wfm-mon 2 }

audioDisp       OBJECT IDENTIFIER ::= { wfm-mon 4 }

wfm             OBJECT IDENTIFIER ::= { wfm-mon 5 }

vec             OBJECT IDENTIFIER ::= { wfm-mon 6 }

arr             OBJECT IDENTIFIER ::= { wfm-mon 7 }

lgt             OBJECT IDENTIFIER ::= { wfm-mon 8 }

dmd             OBJECT IDENTIFIER ::= { wfm-mon 9 }

pict            OBJECT IDENTIFIER ::= { wfm-mon 10 }

sdistat         OBJECT IDENTIFIER ::= { wfm-mon 11 }

preset          OBJECT IDENTIFIER ::= { wfm-mon 12 }

gamut           OBJECT IDENTIFIER ::= { wfm-mon 13 }

eye             OBJECT IDENTIFIER ::= { wfm-mon 14 }

jitter          OBJECT IDENTIFIER ::= { wfm-mon 15 }

logstat         OBJECT IDENTIFIER ::= { wfm-mon 16 }

audio           OBJECT IDENTIFIER ::= { wfm-mon 17 }

audioIo         OBJECT IDENTIFIER ::= { wfm-mon 18 }

traps           OBJECT IDENTIFIER ::= { wfm-mon 19 }

alarm           OBJECT IDENTIFIER ::= { wfm-mon 20 }

ltc             OBJECT IDENTIFIER ::= { wfm-mon 21 }

timing          OBJECT IDENTIFIER ::= { wfm-mon 22 }

audioAnaDisp    OBJECT IDENTIFIER ::= { wfm-mon 23 }

display         OBJECT IDENTIFIER ::= { wfm-mon 24 }

comp            OBJECT IDENTIFIER ::= { wfm-mon 25 }

cableMeter      OBJECT IDENTIFIER ::= { wfm-mon 26 }

anc             OBJECT IDENTIFIER ::= { wfm-mon 27 }

datalist        OBJECT IDENTIFIER ::= { wfm-mon 28 }

bowtie          OBJECT IDENTIFIER ::= { wfm-mon 29 }

pictqual        OBJECT IDENTIFIER ::= { wfm-mon 30 }

auxData         OBJECT IDENTIFIER ::= { wfm-mon 31 }

audioLoudness   OBJECT IDENTIFIER ::= { wfm-mon 32 }

extref          OBJECT IDENTIFIER ::= { wfm-mon 33 }

generator       OBJECT IDENTIFIER ::= { wfm-mon 34 }

sfp             OBJECT IDENTIFIER ::= { wfm-mon 35 }

-- 
-- Textual Conventions
-- 
AudioLevel ::= TEXTUAL-CONVENTION
    DISPLAY-HINT "d-2"
    STATUS		current
    DESCRIPTION
		"Audio level in units of dB (x100). Audio mute is represented by the value -999.00 dB."
    SYNTAX		INTEGER

DBLevel ::= TEXTUAL-CONVENTION
    DISPLAY-HINT "d-2"
    STATUS		current
    DESCRIPTION
		"Values in units of dB (x100)."
    SYNTAX		INTEGER

JitterLevel ::= TEXTUAL-CONVENTION
    DISPLAY-HINT "d-2"
    STATUS		current
    DESCRIPTION
		"Jitter level in units of UI (x100)."
    SYNTAX		INTEGER

FrameRate ::= TEXTUAL-CONVENTION
    DISPLAY-HINT "d-2"
    STATUS		current
    DESCRIPTION
		"Frame rate expressed in frame per second (x100)."
    SYNTAX		INTEGER

-- MIB version

wfmMonMibVer    OBJECT-TYPE
    SYNTAX 	DisplayString
    MAX-ACCESS 	read-only
    STATUS 	current
    DESCRIPTION 	"MIB version implemented by SNMP agent.  This MIB document is version 1.25"

    ::= { wfm-mon 255 }

-- 
-- gen Group
-- Global instrument parameters 

ipAddress       OBJECT-TYPE
    SYNTAX 	DisplayString
    MAX-ACCESS 	read-only
    STATUS 	current
    DESCRIPTION 	"Network IP Address of the primary network interface"

    ::= { gen 1 }


subnetMask      OBJECT-TYPE
    SYNTAX 	DisplayString
    MAX-ACCESS 	read-only
    STATUS 	current
    DESCRIPTION 	"Subnet mask of the primary network interface"

    ::= { gen 2 }


swVersion       OBJECT-TYPE
    SYNTAX 	DisplayString
    MAX-ACCESS 	read-only
    STATUS 	current
    DESCRIPTION 	"Software version and creation date"

    ::= { gen 3 }


fpgaVersions    OBJECT-TYPE
    SYNTAX 	DisplayString
    MAX-ACCESS 	read-only
    STATUS 	current
    DESCRIPTION 	"List of versions for each programmable logic part"

    ::= { gen 4 }


fpVersion       OBJECT-TYPE
    SYNTAX 	DisplayString
    MAX-ACCESS 	read-only
    STATUS 	current
    DESCRIPTION 	"Hardware and Software version of front panel"

    ::= { gen 5 }


instId          OBJECT-TYPE
    SYNTAX 	DisplayString
    MAX-ACCESS 	read-write
    STATUS 	current
    DESCRIPTION 	"Instrument name"

    ::= { gen 6 }


displayMode     OBJECT-TYPE
    SYNTAX 	INTEGER {
        none(0),
        wfm(1),
        vec(2),
        lightning(3),
        picture(4),
        arrowhead(5),
        diamond(6),
        status-log(7),
        audio-bars(8),
        ltc(9),
        timeref(10),
        status-alarm(11),
        status-video(12),
        status-audio(13),
        split-diamond(14),
        audio-liss(15),
        audio-chanstat(16),
        audio-embStatus(17),
        multi(18),
        eye(19),
        jitter(20),
        data(21),
        bowtie(22),
        sdiStatus(23),
        ancData(24),
        status-auxData(25),
        audio-surround(26),
        status-dolby(27),
        status-aribB39(28),
        status-aribB37(29),
        status-aribB35(30),
        status-aribTRB23-2(31),
        status-aribTRB23-1(32),
        status-aribTRB22(33),
        status-aribSummary(34),
        status-audioCtl(35),
        status-av-delay(36),
        spearhead(37),
        loudness-display(38),
        audio-loudness(39),
        ext-ref-waveform(40),
        diag-monitor(41),
        diamond-quad-3D(42),
        generator-status(43),
        status-sfp(44),
        aud-generator-status(45),
        asi-pid-list(46)
    }
    MAX-ACCESS 	read-write
    STATUS 	current
    DESCRIPTION 	"Display Mode in selected tile"

    ::= { displayModeEntry 1 }


lineSelectEnable OBJECT-TYPE
    SYNTAX 	INTEGER {
        off(0),
        on(1)
    }
    MAX-ACCESS 	read-write
    STATUS 	current
    DESCRIPTION 	"Enable line select mode in selected tile"

    ::= { displayModeEntry 2 }


multiInputDisplay OBJECT-TYPE
    SYNTAX 	INTEGER {
        off(0),
        on(1)
    }
    MAX-ACCESS 	read-write
    STATUS 	current
    DESCRIPTION 	"Enables camera balance mode within a tile."

    ::= { displayModeEntry 3 }


trace3dDisplay  OBJECT-TYPE
    SYNTAX 	INTEGER {
        raw(0),
        overlay(1),
        left(2),
        right(3),
        leftMinusRight(4),
        rightMinusLeft(5)
    }
    MAX-ACCESS 	read-write
    STATUS 	current
    DESCRIPTION 	"Selects 3D display mode for trace displays.  Raw is only valid for frame-compatible 3D formats and will display as overlay for all other 3D formats."

    ::= { displayModeEntry 4 }


displayModeTable OBJECT-TYPE
    SYNTAX 	SEQUENCE OF DisplayModeEntry
    MAX-ACCESS 	not-accessible
    STATUS 	current
    DESCRIPTION 	"Table for display modes"

    ::= { gen 7 }


displayModeEntry OBJECT-TYPE
    SYNTAX 	DisplayModeEntry
    MAX-ACCESS 	not-accessible
    STATUS 	current
    DESCRIPTION 	"A row in the displayMode table"
    INDEX { currTile }

    ::= { displayModeTable 1 }


DisplayModeEntry ::= SEQUENCE {
    displayMode 	INTEGER,
    lineSelectEnable 	INTEGER,
    multiInputDisplay 	INTEGER,
    trace3dDisplay 	INTEGER 
}

ipConfigMode    OBJECT-TYPE
    SYNTAX 	INTEGER {
        manual(0),
        dhcp(1)
    }
    MAX-ACCESS 	read-only
    STATUS 	current
    DESCRIPTION 	"IP address configuration mode of the instrument"

    ::= { gen 8 }


gatewayAddress  OBJECT-TYPE
    SYNTAX 	DisplayString
    MAX-ACCESS 	read-only
    STATUS 	current
    DESCRIPTION 	"Default gateway address for the primary network interface"

    ::= { gen 9 }


macAddress      OBJECT-TYPE
    SYNTAX 	DisplayString
    MAX-ACCESS 	read-only
    STATUS 	current
    DESCRIPTION 	"Ethernet MAC address for the primary network interface"

    ::= { gen 10 }


snmpPublicCommStr OBJECT-TYPE
    SYNTAX 	DisplayString (SIZE(1..15))
    MAX-ACCESS 	read-write
    STATUS 	current
    DESCRIPTION 	"Public community string used to authenticate all SNMP GET requests (write-only)"

    ::= { gen 11 }


snmpPrivateCommStr OBJECT-TYPE
    SYNTAX 	DisplayString (SIZE(1..15))
    MAX-ACCESS 	read-write
    STATUS 	current
    DESCRIPTION 	"Private community string used to authenticate all SNMP SET/GET requests (write-only)"

    ::= { gen 12 }


webAccess       OBJECT-TYPE
    SYNTAX 	INTEGER {
        off(0),
        on(1)
    }
    MAX-ACCESS 	read-write
    STATUS 	current
    DESCRIPTION 	"Enable/disable access to web interface and remote user interface"

    ::= { gen 13 }


hwFaultCondition OBJECT-TYPE
    SYNTAX 	DisplayString
    MAX-ACCESS 	read-only
    STATUS 	current
    DESCRIPTION 	"List of current fault conditions detected by instrument"

    ::= { gen 14 }


viewDiagLog     OBJECT-TYPE
    SYNTAX 	INTEGER {
        off(0),
        on(1)
    }
    MAX-ACCESS 	read-write
    STATUS 	current
    DESCRIPTION 	"Causes the instrument to display the diagnostic log (write only)"

    ::= { gen 15 }


diagLogClear    OBJECT-TYPE
    SYNTAX 	INTEGER {
        off(0),
        on(1)
    }
    MAX-ACCESS 	read-write
    STATUS 	current
    DESCRIPTION 	"Causes the instrument to clear diagnostic log (write only)"

    ::= { gen 16 }


diagLogPage     OBJECT-TYPE
    SYNTAX 	INTEGER (1..10000)
    MAX-ACCESS 	read-write
    STATUS 	current
    DESCRIPTION 	"Causes the instrument to display a particular page of the diagnostic log. If page number given is more than the available pages, first page will be displayed. If page number is zero, last page is displayed (write only)"

    ::= { gen 17 }


timeOfDay       OBJECT-TYPE
    SYNTAX 	DisplayString
    MAX-ACCESS 	read-write
    STATUS 	current
    DESCRIPTION 	"The current time of day for the instrument"

    ::= { gen 18 }


optionsInstalled OBJECT-TYPE
    SYNTAX 	DisplayString
    MAX-ACCESS 	read-only
    STATUS 	current
    DESCRIPTION 	"List of options installed in the instrument"

    ::= { gen 19 }


aribDisplay     OBJECT-TYPE
    SYNTAX 	INTEGER {
        off(0),
        on(1)
    }
    MAX-ACCESS 	read-write
    STATUS 	current
    DESCRIPTION 	"Enable/disable access to the ARIB displays"

    ::= { gen 20 }


hwVersions      OBJECT-TYPE
    SYNTAX 	DisplayString
    MAX-ACCESS 	read-only
    STATUS 	current
    DESCRIPTION 	"Hardware versions"

    ::= { gen 21 }


statusBar       OBJECT-TYPE
    SYNTAX 	INTEGER {
        bottom(0),
        top(1)
    }
    MAX-ACCESS 	read-write
    STATUS 	deprecated
    DESCRIPTION 	"Location of status bar in user interface (bottom or top)"

    ::= { gen 22 }


screenSaver     OBJECT-TYPE
    SYNTAX 	INTEGER {
        off(0),
        on(1)
    }
    MAX-ACCESS 	read-write
    STATUS 	current
    DESCRIPTION 	"Enable/disable display of screen saver (if on, screen saver is displayed after the screen saver wait time, if there is no UI activity)."

    ::= { gen 23 }


ssWaitTime      OBJECT-TYPE
    SYNTAX 	INTEGER (1..299997000)
    MAX-ACCESS 	read-write
    STATUS 	current
    DESCRIPTION 	"Screen saver wait time (amount of waiting time before the screen saver is initiated)"

    ::= { gen 24 }


uiWakeupOnAlarm OBJECT-TYPE
    SYNTAX 	INTEGER {
        off(0),
        on(1)
    }
    MAX-ACCESS 	read-write
    STATUS 	current
    DESCRIPTION 	"Replace the screen saver by user interface, when an alarm condition occurs."

    ::= { gen 25 }


uiWakeupOnWebUI OBJECT-TYPE
    SYNTAX 	INTEGER {
        off(0),
        on(1)
    }
    MAX-ACCESS 	read-write
    STATUS 	current
    DESCRIPTION 	"Replace the screen saver by user interface, when the user makes a change from Java applet."

    ::= { gen 26 }


uiWakeupOnSnmp  OBJECT-TYPE
    SYNTAX 	INTEGER {
        off(0),
        on(1)
    }
    MAX-ACCESS 	read-write
    STATUS 	current
    DESCRIPTION 	"Replace the screen saver by user interface, when the user makes a change using SNMP command."

    ::= { gen 27 }


ssDisplaySpeed  OBJECT-TYPE
    SYNTAX 	INTEGER (1..10)
    MAX-ACCESS 	read-write
    STATUS 	current
    DESCRIPTION 	"Speed at which the sceen saver pattern is displayed in screen saver mode"

    ::= { gen 28 }


currChan        OBJECT-TYPE
    SYNTAX 	INTEGER {
        chan1(0),
        chan2(1)
    }
    MAX-ACCESS 	not-accessible
    STATUS 	current
    DESCRIPTION 	"Currently Selected Channel. This is used as index in tables"

    ::= { gen 29 }


currSlot        OBJECT-TYPE
    SYNTAX 	INTEGER {
        slot1(0),
        slot2(1),
        slot3(2)
    }
    MAX-ACCESS 	not-accessible
    STATUS 	current
    DESCRIPTION 	"Currently Selected Slot. This is used as index in tables"

    ::= { gen 30 }


usbStatus       OBJECT-TYPE
    SYNTAX 	INTEGER {
        device-not-connected(0),
        device-not-mounted(1),
        device-mounted(2)
    }
    MAX-ACCESS 	read-write
    STATUS 	current
    DESCRIPTION 	"Get returns the status of the USB device connected to the instrument. In set operation, device-not-mounted(1) value can be used to unmount and device-mounted(2) can be used to mount the device."

    ::= { gen 31 }


fpEnable        OBJECT-TYPE
    SYNTAX 	INTEGER {
        off(0),
        on(1)
    }
    MAX-ACCESS 	read-write
    STATUS 	current
    DESCRIPTION 	"Network front panel enable"

    ::= { gen 32 }


fp1NetworkAddr  OBJECT-TYPE
    SYNTAX 	DisplayString
    MAX-ACCESS 	read-write
    STATUS 	current
    DESCRIPTION 	"Network address of remote front panel 1"

    ::= { gen 33 }


fp2NetworkAddr  OBJECT-TYPE
    SYNTAX 	DisplayString
    MAX-ACCESS 	read-write
    STATUS 	current
    DESCRIPTION 	"Network address of remote front panel 2"

    ::= { gen 34 }


fp3NetworkAddr  OBJECT-TYPE
    SYNTAX 	DisplayString
    MAX-ACCESS 	read-write
    STATUS 	current
    DESCRIPTION 	"Network address of remote front panel 3"

    ::= { gen 35 }


fp4NetworkAddr  OBJECT-TYPE
    SYNTAX 	DisplayString
    MAX-ACCESS 	read-write
    STATUS 	current
    DESCRIPTION 	"Network address of remote front panel 4"

    ::= { gen 36 }


fp1PortNumber   OBJECT-TYPE
    SYNTAX 	INTEGER
    MAX-ACCESS 	read-write
    STATUS 	current
    DESCRIPTION 	"Port number of Remote Front Panel 1"

    ::= { gen 37 }


fp2PortNumber   OBJECT-TYPE
    SYNTAX 	INTEGER
    MAX-ACCESS 	read-write
    STATUS 	current
    DESCRIPTION 	"Port number of Remote Front Panel 2"

    ::= { gen 38 }


fp3PortNumber   OBJECT-TYPE
    SYNTAX 	INTEGER
    MAX-ACCESS 	read-write
    STATUS 	current
    DESCRIPTION 	"Port number of Remote Front Panel 3"

    ::= { gen 39 }


fp4PortNumber   OBJECT-TYPE
    SYNTAX 	INTEGER
    MAX-ACCESS 	read-write
    STATUS 	current
    DESCRIPTION 	"Port number of Remote Front Panel 4"

    ::= { gen 40 }


multiInputEnable OBJECT-TYPE
    SYNTAX 	INTEGER {
        off(0),
        on(1)
    }
    MAX-ACCESS 	read-write
    STATUS 	current
    DESCRIPTION 	"Global camera balance mode enable used to enablethe camera balance mode operations within the instrument.When off, all camera balance mode options and controls arehidden and camera balance mode is disabled."

    ::= { gen 41 }

-- 
-- input group. Input variables.

videoIn         OBJECT-TYPE
    SYNTAX 	DisplayString
    MAX-ACCESS 	read-write
    STATUS 	current
    DESCRIPTION 	"Current video input source.
	The following strings may be used to identify a video input source.
	Input 1a, Input 1b, Input 2a, Input 2b, 1A, 1B, 2A, 2B, input 1a.1, input 1a.2, input 1b.1, input 1b.2, input 2a.1, input 2a.2, input 2b.1, input 2b.2  
	SDI A, SDI B, SDI C, SDI D
	Comp A, Comp B, Composite A, Composite B"

    ::= { input 1 }


sdiInStd        OBJECT-TYPE
    SYNTAX 	INTEGER {
        auto(0),
        std-525i-59-94(1),
        std-625i-50(2),
        std-1080i-59-94(3),
        std-1080i-60(4),
        std-720p-59-94(5),
        std-1080p-23-98(6),
        std-1080p-24(7),
        std-1080p-30(8),
        std-1080p-29-97(9),
        std-1080p-25(10),
        std-1080i-50(11),
        std-1035i-60(12),
        std-1035i-59-94(13),
        rp-1080sf-24(14),
        rp-1080sf-23-98(15),
        std-720p-24(16),
        std-720p-23-98(17),
        std-720p-60(18),
        std-720p-50(19),
        std-720p-25(20),
        std-720p-29-97(21),
        std-720p-30(22),
        rp-1080sf-25(23),
        rp-1080sf-29-97(24),
        rp-1080sf-30(25),
        std-1080p-50(26),
        std-1080p-59-94(27),
        std-1080p-60(28),
        std-2048p-30(29),
        std-2048sf-30(30),
        std-2048p-29-97(31),
        std-2048sf-29-97(32),
        std-2048p-25(33),
        std-2048sf-25(34),
        std-2048p-24(35),
        std-2048sf-24(36),
        std-2048p-23-98(37),
        std-2048sf-23-98(38),
        std-2048p-4796(39),
        std-2048i-4796(40),
        std-2048p-48(41),
        std-2048i-48(42),
        std-2048p-50(43),
        std-2048i-50(44),
        std-2048p-5994(45),
        std-2048i-5994(46),
        std-2048p-60(47),
        std-2048i-60(48),
        std-3840p-23-98(49),
        std-3840sf-23-98(50),
        std-3840p-24(51),
        std-3840sf-24(52),
        std-3840p-25(53),
        std-3840sf-25(54),
        std-3840p-2997(55),
        std-3840sf-2997(56),
        std-3840p-30(57),
        std-3840sf-30(58),
        std-3840p-4796(59),
        std-3840i-4796(60),
        std-3840p-48(61),
        std-3840i-48(62),
        std-3840p-50(63),
        std-3840i-50(64),
        std-3840p-5994(65),
        std-3840i-5994(66),
        std-3840p-60(67),
        std-3840i-60(68),
        std-4096p-23-98(69),
        std-4096sf-23-98(70),
        std-4096p-24(71),
        std-4096sf-24(72),
        std-4096p-25(73),
        std-4096sf-25(74),
        std-4096p-2997(75),
        std-4096sf-2997(76),
        std-4096p-30(77),
        std-4096sf-30(78),
        std-4096p-4796(79),
        std-4096i-4796(80),
        std-4096p-48(81),
        std-4096i-48(82),
        std-4096p-50(83),
        std-4096i-50(84),
        std-4096p-5994(85),
        std-4096i-5994(86),
        std-4096p-60(87),
        std-4096i-60(88)
    }
    MAX-ACCESS 	read-write
    STATUS 	current
    DESCRIPTION 	"Format of the current video input source. When set to auto(0), input format selection is based on the detected format of the video input signal."

    ::= { input 2 }


compInStd       OBJECT-TYPE
    SYNTAX 	INTEGER {
        auto(0),
        ntsc(1),
        ntsc-ns(2),
        pal(3)
    }
    MAX-ACCESS 	read-write
    STATUS 	current
    DESCRIPTION 	"Composite input standard."

    ::= { input 3 }


refSrc          OBJECT-TYPE
    SYNTAX 	INTEGER {
        internal(0),
        external(1)
    }
    MAX-ACCESS 	read-write
    STATUS 	current
    DESCRIPTION 	"Current reference source (Internal/External)."

    ::= { input 4 }


refInStd        OBJECT-TYPE
    SYNTAX 	INTEGER {
        auto(0),
        ntsc(1),
        pal(2),
        std-1080i-59-94(3),
        std-1080i-60(4),
        std-720p-59-94(5),
        std-1080p-23-98(6),
        std-1080p-24(7),
        std-1080p-25(8),
        std-1080i-50(9),
        std-720p-50(10),
        std-720p-60(11),
        std-1080-30p(12),
        std-1080-2997p(13),
        std-720-30p(14),
        std-720-2997p(15),
        std-720-25p(16),
        std-720-24p(17),
        std-720-23-98p(18),
        std-1080sf-23-98(19),
        std-1080sf-24(20)
    }
    MAX-ACCESS 	read-write
    STATUS 	current
    DESCRIPTION 	"Format of the external reference source. When set to auto(0), reference format selection is based on the detected format of the reference input signal."

    ::= { input 5 }


refLocked       OBJECT-TYPE
    SYNTAX 	INTEGER {
        locked(0),
        unlocked(1)
    }
    MAX-ACCESS 	read-only
    STATUS 	current
    DESCRIPTION 	"Reference input status (locked/unlokced)."

    ::= { input 6 }


sdiSetup        OBJECT-TYPE
    SYNTAX 	INTEGER {
        off(0),
        on(1)
    }
    MAX-ACCESS 	read-write
    STATUS 	current
    DESCRIPTION 	"Enable/disable pseudo composite setup in Waveform and Arrohead displays"

    ::= { input 8 }


lineSelect      OBJECT-TYPE
    SYNTAX 	INTEGER (1..4500)
    MAX-ACCESS 	read-write
    STATUS 	current
    DESCRIPTION 	"Select line in current field."

    ::= { input 15 }


fieldSelect     OBJECT-TYPE
    SYNTAX 	INTEGER {
        all(0),
        f1(1),
        f2(2),
        f3(3),
        f4(4),
        f5(5),
        f6(6),
        f7(7),
        f8(8),
        fields-odd(9),
        fields-even(10)
    }
    MAX-ACCESS 	read-write
    STATUS 	current
    DESCRIPTION 	"Select current field for line select.  For dual link fast progressive video formats, use fields-even to select only lines from link A and use fields-odd to select lines from link B"

    ::= { input 16 }


activeTimeCode  OBJECT-TYPE
    SYNTAX 	DisplayString
    MAX-ACCESS 	read-only
    STATUS 	current
    DESCRIPTION 	"Current timecode value from selected timecode source."

    ::= { input 19 }


timeCodeSrc     OBJECT-TYPE
    SYNTAX 	INTEGER {
        off(0),
        ltc(1),
        vitc(2),
        ancvitc(3),
        ancltc(4),
        auto(5)
    }
    MAX-ACCESS 	read-write
    STATUS 	current
    DESCRIPTION 	"Active timecode source."

    ::= { input 20 }


ltcPresent      OBJECT-TYPE
    SYNTAX 	INTEGER {
        false(0),
        true(1)
    }
    MAX-ACCESS 	read-only
    STATUS 	current
    DESCRIPTION 	"LTC source is present or not."

    ::= { input 21 }


vitcPresent     OBJECT-TYPE
    SYNTAX 	INTEGER {
        false(0),
        true(1)
    }
    MAX-ACCESS 	read-only
    STATUS 	current
    DESCRIPTION 	"VITC source is present or not."

    ::= { input 22 }


timeCodePresent OBJECT-TYPE
    SYNTAX 	INTEGER {
        false(0),
        true(1)
    }
    MAX-ACCESS 	read-only
    STATUS 	current
    DESCRIPTION 	"Timecode is present or not."

    ::= { input 23 }


lineSelectTile  OBJECT-TYPE
    SYNTAX 	INTEGER {
        off(0),
        tile1(1),
        tile2(2),
        tile3(3),
        tile4(4)
    }
    MAX-ACCESS 	read-write
    STATUS 	deprecated
    DESCRIPTION 	"Enable line select for specified tile."

    ::= { input 24 }


sdiStripEavSav  OBJECT-TYPE
    SYNTAX 	INTEGER {
        off(0),
        on(1)
    }
    MAX-ACCESS 	read-write
    STATUS 	current
    DESCRIPTION 	"Strip EAV/SAV/ANC data from video before display"

    ::= { input 25 }


sdiChroma       OBJECT-TYPE
    SYNTAX 	INTEGER {
        offset(0),
        align(1)
    }
    MAX-ACCESS 	read-write
    STATUS 	current
    DESCRIPTION 	"Align Pb and Pr components in waveform displays."

    ::= { input 26 }


extRefStdDet    OBJECT-TYPE
    SYNTAX 	DisplayString
    MAX-ACCESS 	read-only
    STATUS 	current
    DESCRIPTION 	"Detected format of the external reference signal."

    ::= { input 37 }


inpSigStdDet    OBJECT-TYPE
    SYNTAX 	DisplayString
    MAX-ACCESS 	read-only
    STATUS 	current
    DESCRIPTION 	"Detected format of the current video input signal."

    ::= { input 38 }


hdColorimetry   OBJECT-TYPE
    SYNTAX 	INTEGER {
        auto(0),
        itu709(1),
        smpte240m(2),
        dci-p3(3),
        itu601(4),
        sRGB(5),
        smpte-c(6),
        ebu3213(7),
        itu2020(8),
        proPhoto(9),
        smpte2048(10),
        adobeRgb(11),
        adobeWide(12),
        p22(13),
        NTSC(14),
        ACES(15),
        canon-dci-p3-plus(16),
        canon-cimena(17)
    }
    MAX-ACCESS 	read-write
    STATUS 	current
    DESCRIPTION 	"Select colorimetry standards for HD formats."

    ::= { input 39 }


ancTimeCode     OBJECT-TYPE
    SYNTAX 	DisplayString
    MAX-ACCESS 	read-only
    STATUS 	current
    DESCRIPTION 	"Report ANC timecode value."

    ::= { input 40 }


dep-ancDID      OBJECT-TYPE
    SYNTAX 	INTEGER (1..255)
    MAX-ACCESS 	read-write
    STATUS 	deprecated
    DESCRIPTION 	"anc data ID (DID)."

    ::= { input 41 }


dep-ancSDID     OBJECT-TYPE
    SYNTAX 	INTEGER (0..255)
    MAX-ACCESS 	read-write
    STATUS 	deprecated
    DESCRIPTION 	"anc secondary data ID (DDID)."

    ::= { input 42 }


ancDataMode     OBJECT-TYPE
    SYNTAX 	INTEGER {
        ancDataRaw(1),
        ancDataDecoded(2)
    }
    MAX-ACCESS 	read-write
    STATUS 	current
    DESCRIPTION 	"anc data mode [raw(ancData) or decoded(aribB39)]."

    ::= { input 43 }


ccMissing       OBJECT-TYPE
    SYNTAX 	INTEGER {
        cc-absent(0),
        cc-present(1),
        cc-status-unknown(2)
    }
    MAX-ACCESS 	read-only
    STATUS 	current
    DESCRIPTION 	"Report closed caption presence."

    ::= { input 44 }


ccTransport     OBJECT-TYPE
    SYNTAX 	INTEGER {
        cc-auto(0),
        cc-EIA-608-VBI(1),
        cc-EIA-608-ANC(2),
        cc-EIA-608-708(4),
        cc-EIA-708(5),
        teletext-VBI(6),
        teletext-OP47-SDP(7),
        teletext-OP47-Multi(8)
    }
    MAX-ACCESS 	read-write
    STATUS 	deprecated
    DESCRIPTION 	"Report closed caption transport."

    ::= { input 45 }


ccLineDetectMode OBJECT-TYPE
    SYNTAX 	INTEGER {
        auto(0),
        manual(1)
    }
    MAX-ACCESS 	read-write
    STATUS 	current
    DESCRIPTION 	"Selects closed caption line selection mode."

    ::= { input 46 }


ccLineNum       OBJECT-TYPE
    SYNTAX 	INTEGER (5..25)
    MAX-ACCESS 	read-write
    STATUS 	current
    DESCRIPTION 	"Selects line number for closed caption data in manual selection mode."

    ::= { input 47 }


ccDetected      OBJECT-TYPE
    SYNTAX 	DisplayString
    MAX-ACCESS 	read-only
    STATUS 	deprecated
    DESCRIPTION 	"Reports types of closed captions detected."

    ::= { input 48 }


ccService608    OBJECT-TYPE
    SYNTAX 	INTEGER {
        cc1(1),
        cc2(2),
        cc3(3),
        cc4(4),
        text1(5),
        text2(6),
        text3(7),
        text4(8)
    }
    MAX-ACCESS 	read-write
    STATUS 	deprecated
    DESCRIPTION 	"closed caption service 608 channel selection."

    ::= { input 49 }


ccService708    OBJECT-TYPE
    SYNTAX 	INTEGER {
        service1(1),
        service2(2),
        service3(3),
        service4(4),
        service5(5),
        service6(6)
    }
    MAX-ACCESS 	read-write
    STATUS 	deprecated
    DESCRIPTION 	"closed caption service 708 channel selection."

    ::= { input 50 }


gcGndClosurePort OBJECT-TYPE
    SYNTAX 	INTEGER {
        disable(0),
        enable(1)
    }
    MAX-ACCESS 	read-write
    STATUS 	deprecated
    DESCRIPTION 	"Enable/disable ground closure port."

    ::= { input 51 }


ccRequiredService608 OBJECT-TYPE
    SYNTAX 	BITS {
        text4(0),
        text3(1),
        text2(2),
        text1(3),
        cc4(4),
        cc3(5),
        cc2(6),
        cc1(7)
    }
    MAX-ACCESS 	read-write
    STATUS 	current
    DESCRIPTION 	"Each bit in the octet defines a service as being required. If the service is missing a CC Services(s) missing Alarm may be thrown."

    ::= { input 52 }


ccVBITiming     OBJECT-TYPE
    SYNTAX 	INTEGER {
        normal(0),
        early(1),
        late(2)
    }
    MAX-ACCESS 	read-write
    STATUS 	current
    DESCRIPTION 	"EIA 608 line 21 VBI timing."

    ::= { input 53 }


audCtl272Grp    OBJECT-TYPE
    SYNTAX 	BITS {
        grp4(0),
        grp3(1),
        grp2(2),
        grp1(3)
    }
    MAX-ACCESS 	read-write
    STATUS 	current
    DESCRIPTION 	"Enable/disable triggering of audCtrlPktMissing alarms for each of the audio control groups from Group1 to Group4, if they are missing from the input signal. This configuration is applicable only for SD standards."

    ::= { input 54 }


audCtl299Grp    OBJECT-TYPE
    SYNTAX 	BITS {
        grp4(0),
        grp3(1),
        grp2(2),
        grp1(3)
    }
    MAX-ACCESS 	read-write
    STATUS 	current
    DESCRIPTION 	"Enable/disable triggering of audCtrlPktMissing alarms for each of the audio control groups from Group1 to Group4, if they are missing from the input signal. This configuration is applicable only for HD standards."

    ::= { input 55 }


ancB37ReqSvc    OBJECT-TYPE
    SYNTAX 	BITS {
        hd(0),
        sd(1),
        analog(2),
        mobile(3)
    }
    MAX-ACCESS 	read-write
    STATUS 	current
    DESCRIPTION 	"Enable/disable triggering of CC Service missing alarms for each of the services for CC HD, CC SD, CC Analog and CC Mobile, if the services are missing from the ARIB B37 stream."

    ::= { input 56 }


sampleSelect    OBJECT-TYPE
    SYNTAX 	INTEGER (0..8250)
    MAX-ACCESS 	read-write
    STATUS 	current
    DESCRIPTION 	"Select sample number."

    ::= { input 57 }


inputMode       OBJECT-TYPE
    SYNTAX 	INTEGER {
        single(0),
        simultaneous(1),
        master-control(2),
        uhd-4k-video(3)
    }
    MAX-ACCESS 	read-write
    STATUS 	current
    DESCRIPTION 	"Select the input mode - single, simultaneous or UHD/4K video Mode."

    ::= { input 58 }


sdiTransportType OBJECT-TYPE
    SYNTAX 	INTEGER {
        auto(0),
        single-link-hd-sdi(1),
        dual-link-hd-sdi(2),
        sdi-3g-level-A(3),
        sdi-3g-level-B(4),
        sdi-3g-dual-link(5),
        quad-link-hd(6),
        sdi-3g-quad-link(7)
    }
    MAX-ACCESS 	read-write
    STATUS 	current
    DESCRIPTION 	"Select SDI transport type."

    ::= { input 59 }


sdiSampleStruct OBJECT-TYPE
    SYNTAX 	INTEGER {
        auto(0),
        hd-sdi-422(1),
        ycbcr-422-10b(2),
        ycbcr-422-12b(3),
        ycbcrA-4224-12b(4),
        ycbcr-444-10b(5),
        ycbcrA-4444-10b(6),
        ycbcr-444-12b(7),
        rgb-444-10b(8),
        rgbA-4444-10b(9),
        rgb-444-12b(10),
        xyz-444-10b(11),
        xyzA-4444-10b(12),
        xyz-444-12b(13)
    }
    MAX-ACCESS 	read-write
    STATUS 	current
    DESCRIPTION 	"Select the SDI sample structure."

    ::= { input 60 }


dualLinkThreshold OBJECT-TYPE
    SYNTAX 	INTEGER (1..32)
    MAX-ACCESS 	read-write
    STATUS 	current
    DESCRIPTION 	"Select the SDI dual link threshold value."

    ::= { input 61 }


linkSelect      OBJECT-TYPE
    SYNTAX 	INTEGER {
        link-a(0),
        link-b(1)
    }
    MAX-ACCESS 	read-write
    STATUS 	current
    DESCRIPTION 	"Select the link (Link A or Link B) in Dual Link mode."

    ::= { input 62 }


groundClosureMode OBJECT-TYPE
    SYNTAX 	INTEGER {
        direct(0),
        encoded(1),
        tally(2),
        loudLog(3)
    }
    MAX-ACCESS 	read-write
    STATUS 	current
    DESCRIPTION 	"Select the ground closure mode - direct(legacy), encoded, camera tally, or loudness event logging."

    ::= { input 63 }


afdData         OBJECT-TYPE
    SYNTAX 	DisplayString
    MAX-ACCESS 	read-only
    STATUS 	current
    DESCRIPTION 	"SMPTE 2016 Active Format Description data."

    ::= { input 64 }


bar1Data        OBJECT-TYPE
    SYNTAX 	DisplayString
    MAX-ACCESS 	read-only
    STATUS 	current
    DESCRIPTION 	"SMPTE 2016 Bar1 data."

    ::= { input 65 }


bar2Data        OBJECT-TYPE
    SYNTAX 	DisplayString
    MAX-ACCESS 	read-only
    STATUS 	current
    DESCRIPTION 	"SMPTE 2016 Bar2 data."

    ::= { input 66 }


wssData         OBJECT-TYPE
    SYNTAX 	DisplayString
    MAX-ACCESS 	read-only
    STATUS 	current
    DESCRIPTION 	"Wide Screen Signalling information."

    ::= { input 67 }


viData          OBJECT-TYPE
    SYNTAX 	DisplayString
    MAX-ACCESS 	read-only
    STATUS 	current
    DESCRIPTION 	"RP186 Video Index information."

    ::= { input 68 }


ccRequiredService708 OBJECT-TYPE
    SYNTAX 	BITS {
        service6(0),
        service5(1),
        service4(2),
        service3(3),
        service2(4),
        service1(5)
    }
    MAX-ACCESS 	read-write
    STATUS 	current
    DESCRIPTION 	"Each bit in the octet defines a service as being required. If the service is missing a CC Services(s) missing Alarm may be thrown."

    ::= { input 69 }


ccStatus608     OBJECT-TYPE
    SYNTAX 	INTEGER {
        missing(0),
        unused(1),
        vbi(2),
        s334-raw(3),
        s334-cdp(4)
    }
    MAX-ACCESS 	read-only
    STATUS 	current
    DESCRIPTION 	"Returns transport on which CEA608 captions are being carried."

    ::= { input 70 }


ccStatus708     OBJECT-TYPE
    SYNTAX 	INTEGER {
        missing(0),
        unused(1),
        s334-cdp(2)
    }
    MAX-ACCESS 	read-only
    STATUS 	current
    DESCRIPTION 	"Returns transport on which CEA708 captions are being carried."

    ::= { input 71 }


ccStatusWst     OBJECT-TYPE
    SYNTAX 	INTEGER {
        missing(0),
        unused(1),
        vbi(2),
        op47-sdp(3),
        op47-multi(4)
    }
    MAX-ACCESS 	read-only
    STATUS 	current
    DESCRIPTION 	"Returns transport on which Wst captions are being carried"

    ::= { input 72 }


ccServices608   OBJECT-TYPE
    SYNTAX 	BITS {
        text4(0),
        text3(1),
        text2(2),
        text1(3),
        cc4(4),
        cc3(5),
        cc2(6),
        cc1(7)
    }
    MAX-ACCESS 	read-only
    STATUS 	current
    DESCRIPTION 	"Each bit in the octet defines a service that is present."

    ::= { input 73 }


ccServices708   OBJECT-TYPE
    SYNTAX 	BITS {
        service6(0),
        service5(1),
        service4(2),
        service3(3),
        service2(4),
        service1(5)
    }
    MAX-ACCESS 	read-only
    STATUS 	current
    DESCRIPTION 	"Each bit in the octet defines a service that is present."

    ::= { input 74 }


ccVbi608Line    OBJECT-TYPE
    SYNTAX 	INTEGER
    MAX-ACCESS 	read-only
    STATUS 	current
    DESCRIPTION 	"Returns the line number for VBI CEA608 captions or 0 if not present."

    ::= { input 75 }


xdsPresent      OBJECT-TYPE
    SYNTAX 	INTEGER {
        missing(0),
        present(1)
    }
    MAX-ACCESS 	read-only
    STATUS 	current
    DESCRIPTION 	"Returns presence status of xds."

    ::= { input 76 }


rp207Present    OBJECT-TYPE
    SYNTAX 	INTEGER {
        missing(0),
        present(1)
    }
    MAX-ACCESS 	read-only
    STATUS 	current
    DESCRIPTION 	"Returns presence status of rp207."

    ::= { input 77 }


tsid            OBJECT-TYPE
    SYNTAX 	INTEGER
    MAX-ACCESS 	read-only
    STATUS 	current
    DESCRIPTION 	"Returns the TSID if present ."

    ::= { input 78 }


cdpStatus       OBJECT-TYPE
    SYNTAX 	INTEGER {
        missing(0),
        present(1)
    }
    MAX-ACCESS 	read-only
    STATUS 	current
    DESCRIPTION 	"Indicates weather caption data packets are present."

    ::= { input 79 }


cgmsPresent     OBJECT-TYPE
    SYNTAX 	DisplayString
    MAX-ACCESS 	read-only
    STATUS 	current
    DESCRIPTION 	"Returns CGMS-A Status."

    ::= { input 80 }


cdpFrameRate    OBJECT-TYPE
    SYNTAX 	DisplayString
    MAX-ACCESS 	read-only
    STATUS 	current
    DESCRIPTION 	"Returns frame rate incoded in CDP."

    ::= { input 81 }


vchipQueryRating OBJECT-TYPE
    SYNTAX 	DisplayString
    MAX-ACCESS 	read-only
    STATUS 	current
    DESCRIPTION 	"Returns the content advisory in the same manner as the UI."

    ::= { input 82 }


ccVbiWstLines   OBJECT-TYPE
    SYNTAX 	OCTET STRING
    MAX-ACCESS 	read-only
    STATUS 	current
    DESCRIPTION 	"Returns the number of lines for VBI WST Teletext."

    ::= { input 83 }


rcdPresent      OBJECT-TYPE
    SYNTAX 	INTEGER {
        missing(0),
        xds(1),
        rp207(2),
        xds-rp207(3)
    }
    MAX-ACCESS 	read-only
    STATUS 	current
    DESCRIPTION 	"Returns rcd (broadcast flag) status."

    ::= { input 84 }


cdpCcDataSize   OBJECT-TYPE
    SYNTAX 	OCTET STRING (SIZE(0..2))
    MAX-ACCESS 	read-only
    STATUS 	current
    DESCRIPTION 	"Indicates the number of bytes of 608 and 708 payload in the CDP."

    ::= { input 85 }


timeCodeSelection OBJECT-TYPE
    SYNTAX 	INTEGER {
        ltc(0),
         vitc(1),
         ancvitc(2),
         none(3),
         anctlc(4),
         reserved1(5),
         reserved2(6),
         reserved3(7),
         auto(8)
    }
    MAX-ACCESS 	read-write
    STATUS 	current
    DESCRIPTION 	"The timecode source for the indicated monitoring channel."

    ::= { input 86 }


currentTimeCode OBJECT-TYPE
    SYNTAX 	DisplayString
    MAX-ACCESS 	read-only
    STATUS 	current
    DESCRIPTION 	"Returns the formatted timecode on the monitoring channel, or 'missing'."

    ::= { input 87 }


vitcStatus      OBJECT-TYPE
    SYNTAX 	INTEGER {
        missing(0),
        present(1),
        error(2)
    }
    MAX-ACCESS 	read-only
    STATUS 	current
    DESCRIPTION 	"Returns status of VITC on the monitored channel."

    ::= { input 88 }


ancVitcStatus   OBJECT-TYPE
    SYNTAX 	INTEGER {
        missing(0),
        present(1),
        error(2)
    }
    MAX-ACCESS 	read-only
    STATUS 	current
    DESCRIPTION 	"Returns status of ancVITC on the monitored channel."

    ::= { input 89 }


ancLtcStatus    OBJECT-TYPE
    SYNTAX 	INTEGER {
        missing(0),
        present(1),
        error(2)
    }
    MAX-ACCESS 	read-only
    STATUS 	current
    DESCRIPTION 	"Returns status of ancLTC on the monitored channel."

    ::= { input 90 }


ltcStatus       OBJECT-TYPE
    SYNTAX 	INTEGER {
        missing(0),
        present(1),
        error(2)
    }
    MAX-ACCESS 	read-only
    STATUS 	current
    DESCRIPTION 	"Returns status of LTC"

    ::= { input 91 }


vitcLineMode    OBJECT-TYPE
    SYNTAX 	INTEGER {
        auto(0),
        manual(1)
    }
    MAX-ACCESS 	read-write
    STATUS 	current
    DESCRIPTION 	"Selects auto-detect or manual line selection for VITC/DVITC."

    ::= { input 92 }


vitcLineSelect525 OBJECT-TYPE
    SYNTAX 	INTEGER (10..20)
    MAX-ACCESS 	read-write
    STATUS 	current
    DESCRIPTION 	"Line from which to acquire VITC for 525 line formats."

    ::= { input 93 }


vitcLineSelect625 OBJECT-TYPE
    SYNTAX 	INTEGER (6..22)
    MAX-ACCESS 	read-write
    STATUS 	current
    DESCRIPTION 	"Line from which to acquire VITC for  625 line formats."

    ::= { input 94 }


cgmsConfig      OBJECT-TYPE
    SYNTAX 	INTEGER {
        optional(0),
        required(1),
        forbidden(2)
    }
    MAX-ACCESS 	read-write
    STATUS 	current
    DESCRIPTION 	"CGMS-A configuration."

    ::= { input 95 }


cgmsDisallowSettings OBJECT-TYPE
    SYNTAX 	BITS {
        copy-ok(0),
        already-copied(1),
        one-copy-ok(2),
        do-not-copy(3)
    }
    MAX-ACCESS 	read-write
    STATUS 	current
    DESCRIPTION 	"CGMS-A settings configuration. Selected settings are disallowed."

    ::= { input 96 }


apsDisallowSettings OBJECT-TYPE
    SYNTAX 	BITS {
        no-aps(0),
        psp-only(1),
        psp-2-line-burst(2),
        psp-4-line-burst(3)
    }
    MAX-ACCESS 	read-write
    STATUS 	current
    DESCRIPTION 	"APS settings configuration. Selected settings are disallowed."

    ::= { input 97 }


rcdConfig       OBJECT-TYPE
    SYNTAX 	INTEGER {
        optional(0),
        required(1),
        forbidden(2)
    }
    MAX-ACCESS 	read-write
    STATUS 	current
    DESCRIPTION 	"RCD (broadcast flag) configuration."

    ::= { input 98 }


ccTransport608  OBJECT-TYPE
    SYNTAX 	INTEGER {
        auto(0),
        line-21(1),
        s334-raw(2),
        s334-cdp(3)
    }
    MAX-ACCESS 	read-write
    STATUS 	current
    DESCRIPTION 	"Select the transport for CEA608 captions."

    ::= { input 99 }


ccTransportWst  OBJECT-TYPE
    SYNTAX 	INTEGER {
        auto(0),
        vbi(1),
        op47-sdp(2),
        op47-multi(3)
    }
    MAX-ACCESS 	read-write
    STATUS 	current
    DESCRIPTION 	"Select the transport for WST captions."

    ::= { input 100 }


cea608Required  OBJECT-TYPE
    SYNTAX 	INTEGER {
        no(0),
        yes(1)
    }
    MAX-ACCESS 	read-write
    STATUS 	current
    DESCRIPTION 	"Select whether or not CEA608 is required."

    ::= { input 101 }


cea708Required  OBJECT-TYPE
    SYNTAX 	INTEGER {
        no(0),
        yes(1)
    }
    MAX-ACCESS 	read-write
    STATUS 	current
    DESCRIPTION 	"Select whether or not CEA708 is required."

    ::= { input 102 }


teletextRequired OBJECT-TYPE
    SYNTAX 	INTEGER {
        no(0),
        yes(1)
    }
    MAX-ACCESS 	read-write
    STATUS 	current
    DESCRIPTION 	"Select whether or not teletext is required."

    ::= { input 103 }


syncVuEnable    OBJECT-TYPE
    SYNTAX 	INTEGER {
        off(0),
        on(1)
    }
    MAX-ACCESS 	read-write
    STATUS 	current
    DESCRIPTION 	"Select SyncVu Off or On"

    ::= { input 104 }


multiInputSelect OBJECT-TYPE
    SYNTAX 	DisplayString
    MAX-ACCESS 	read-write
    STATUS 	current
    DESCRIPTION 	"Selects the video inputs in camera balance mode. Value is a list of video input sources as defined by the videoIn OID sperated by commas. Up to four sources may be listed in the string. No duplicates are allowed."

    ::= { input 105 }


sdiInputIndex   OBJECT-TYPE
    SYNTAX 	INTEGER (0..2)
    MAX-ACCESS 	not-accessible
    STATUS 	current
    DESCRIPTION 	"Index For sdi input Table."

    ::= { input 106 }


multiInputLabel OBJECT-TYPE
    SYNTAX 	DisplayString
    MAX-ACCESS 	read-write
    STATUS 	current
    DESCRIPTION 	"Stores or retrieves the custom labels for each of the SDI Inputs for use in camera balance mode displays."

    ::= { sdiEntry 1 }


universalInput  OBJECT-TYPE
    SYNTAX 	INTEGER {
        none(0),
        disable(1),
        sdi(2),
        ltc(3),
        aes(4),
        asi(5)
    }
    MAX-ACCESS 	read-write
    STATUS 	current
    DESCRIPTION 	"Set Universal Input."

    ::= { sdiEntry 2 }


sdiTable        OBJECT-TYPE
    SYNTAX 	SEQUENCE OF SdiEntry
    MAX-ACCESS 	not-accessible
    STATUS 	current
    DESCRIPTION 	"Table for sdi index"

    ::= { input 107 }


sdiEntry        OBJECT-TYPE
    SYNTAX 	SdiEntry
    MAX-ACCESS 	not-accessible
    STATUS 	current
    DESCRIPTION 	"A row in the sidInput table"
    INDEX { currTile }

    ::= { sdiTable 1 }


SdiEntry ::= SEQUENCE {
    multiInputLabel 	DisplayString,
    universalInput 	INTEGER 
}

multiLabelEnable OBJECT-TYPE
    SYNTAX 	INTEGER {
        off(0),
        on(1)
    }
    MAX-ACCESS 	read-write
    STATUS 	current
    DESCRIPTION 	"Select multi input label display Off or On"

    ::= { input 108 }


sample2Select   OBJECT-TYPE
    SYNTAX 	INTEGER (-200..200)
    MAX-ACCESS 	read-write
    STATUS 	current
    DESCRIPTION 	"Select sample 2 number."

    ::= { input 109 }


input3dType     OBJECT-TYPE
    SYNTAX 	INTEGER {
        off(0),
        side-by-side(1),
        top-bottom(2),
        dual-stream(3),
        field-interlace(4)
    }
    MAX-ACCESS 	read-write
    STATUS 	current
    DESCRIPTION 	"Select transport type for 3D video.  Side-by-side, top-bottom, and field interlace provide a frame-compatible 3D picture on HD-SDI.  Dual Stream 3D may be carried on a pair of SDI inputs or within a single 3Gbps level B SDI."

    ::= { input 110 }


input3dCameraSetup OBJECT-TYPE
    SYNTAX 	INTEGER {
        normal(0),
        mirrorLeft(1),
        mirrorRight(2)
    }
    MAX-ACCESS 	read-write
    STATUS 	current
    DESCRIPTION 	"Selections for 3D camera setup.  Mirror left indicates that view from the left camera has been mirrored from left to right"

    ::= { input 111 }


sdiSigSampleStructDet OBJECT-TYPE
    SYNTAX 	DisplayString
    MAX-ACCESS 	read-only
    STATUS 	current
    DESCRIPTION 	"Detected sample structure of the current video input signal."

    ::= { input 112 }


sdiSigTransportDet OBJECT-TYPE
    SYNTAX 	DisplayString
    MAX-ACCESS 	read-only
    STATUS 	current
    DESCRIPTION 	"Detected transport of the current video input signal."

    ::= { input 113 }


hdmiHdcpStatus  OBJECT-TYPE
    SYNTAX 	INTEGER {
        disabled(0),
        initiated(1),
        enabled(2)
    }
    MAX-ACCESS 	read-only
    STATUS 	current
    DESCRIPTION 	"Detect whether HDMI HDCP is enabled or disabled."

    ::= { input 114 }


hdmiColorimetry OBJECT-TYPE
    SYNTAX 	INTEGER {
        none(0),
        smpte170M-ItuRBt601(1),
        ituRBt709-5(2),
        smpte-240(3),
        digiitalCinema(4),
        srgb(5),
        smpte-c(6),
        ebu3213(7),
        itu2020(8),
        proPhoto(9),
        smpte2048(10),
        adobeRgb(11),
        adobeWide(12),
        p22(13),
        NTSC(14),
        ACES(15),
        canon-dci-p3-plus(16)
    }
    MAX-ACCESS 	read-only
    STATUS 	current
    DESCRIPTION 	"Detect HDMI Colorimetry"

    ::= { input 115 }


hdmiColorspace  OBJECT-TYPE
    SYNTAX 	INTEGER {
        ycbcr(0),
        rgb(1),
        xvYcc601(2),
        xvYcc709(3),
        adobeRgb(4),
        adobeYcc601(5)
    }
    MAX-ACCESS 	read-only
    STATUS 	current
    DESCRIPTION 	"Detect HDMI Colorspace"

    ::= { input 116 }


hdmiDeepColor   OBJECT-TYPE
    SYNTAX 	DisplayString
    MAX-ACCESS 	read-only
    STATUS 	current
    DESCRIPTION 	"Bit depth per channel in HDMI video"

    ::= { input 117 }


hdmiQuantizationRange OBJECT-TYPE
    SYNTAX 	INTEGER {
        default(0),
        limited(1),
        full(2)
    }
    MAX-ACCESS 	read-only
    STATUS 	current
    DESCRIPTION 	"Detect HDMI Quantization Range."

    ::= { input 118 }


hdmiAspectRatio OBJECT-TYPE
    SYNTAX 	INTEGER {
        default(0),
        ratio4x3(1),
        ratio16x9(2)
    }
    MAX-ACCESS 	read-only
    STATUS 	current
    DESCRIPTION 	"Detect HDMI Aspect Ratio."

    ::= { input 119 }


hdmiTmdsClockFrequency OBJECT-TYPE
    SYNTAX 	DisplayString
    MAX-ACCESS 	read-only
    STATUS 	current
    DESCRIPTION 	"Detect HDMI TMDS Clock Frequency"

    ::= { input 120 }


hdmiDviOverHdmi OBJECT-TYPE
    SYNTAX 	INTEGER {
        dviPresent(0),
        hdmiPresent(1)
    }
    MAX-ACCESS 	read-only
    STATUS 	current
    DESCRIPTION 	"Detect presence of DVI signal on HDMI, or simply HDMI."

    ::= { input 121 }


hdmiPixelRepRate OBJECT-TYPE
    SYNTAX 	DisplayString
    MAX-ACCESS 	read-only
    STATUS 	current
    DESCRIPTION 	"Detect HDMI Pixel Repetition Rate"

    ::= { input 122 }


hdmiRxHotPlugReset OBJECT-TYPE
    SYNTAX 	INTEGER {
        toggle(0)
    }
    MAX-ACCESS 	read-write
    STATUS 	current
    DESCRIPTION 	"HDMI Receiver Hot Plug Reset.  Setting any value toggles reset."

    ::= { input 123 }


quadSdiMode     OBJECT-TYPE
    SYNTAX 	INTEGER {
        auto(0),
        tile(1),
        sample-interleave(2)
    }
    MAX-ACCESS 	read-write
    STATUS 	current
    DESCRIPTION 	"Select quad sdi mode type, auto, tile, sample interleave "

    ::= { input 124 }


quadLinkThreshold OBJECT-TYPE
    SYNTAX 	INTEGER (1..1024)
    MAX-ACCESS 	read-write
    STATUS 	current
    DESCRIPTION 	"Select the SDI quad link threshold value."

    ::= { input 125 }

-- 
-- audioDisp group
-- Audio Display variables

audCurOutput    OBJECT-TYPE
    SYNTAX 	DisplayString
    MAX-ACCESS 	read-only
    STATUS 	current
    DESCRIPTION 	"Currently selected analog outputs."

    ::= { audioDisp 1 }


audBallistic    OBJECT-TYPE
    SYNTAX 	INTEGER {
        truePeak(0),
        ppm1(1),
        ppm2(2),
        vu(3),
        loudness-F(4),
        loudness-S(5)
    }
    MAX-ACCESS 	read-write
    STATUS 	current
    DESCRIPTION 	"Level Meter ballistics selection for digital audio."

    ::= { audioDisp 2 }


audPkHold       OBJECT-TYPE
    SYNTAX 	INTEGER {
        hold-0P1sec(0),
        hold-0P2sec(1),
        hold-0P4sec(2),
        hold-0P8sec(3),
        hold-1sec(4),
        hold-2sec(5),
        hold-3sec(6),
        hold-4sec(7),
        hold-5sec(8),
        hold-6sec(9),
        hold-7sec(10),
        hold-8sec(11),
        hold-9sec(12),
        hold-10sec(13),
        infinity(14)
    }
    MAX-ACCESS 	read-write
    STATUS 	current
    DESCRIPTION 	"Hold time for digital audio peak level indicator (in seconds)."

    ::= { audioDisp 3 }


audErrorHoldTm  OBJECT-TYPE
    SYNTAX 	INTEGER (1..30)
    MAX-ACCESS 	read-write
    STATUS 	current
    DESCRIPTION 	"The length of time that the digital audio in-bar error messages and over indicators remain on the screen (held) after the error has been removed (in seconds)."

    ::= { audioDisp 4 }


audClipTh       OBJECT-TYPE
    SYNTAX 	INTEGER (1..100)
    MAX-ACCESS 	read-write
    STATUS 	current
    DESCRIPTION 	"Digital audio clip duration threshold (in samples)."

    ::= { audioDisp 5 }


audMuteTh       OBJECT-TYPE
    SYNTAX 	INTEGER (0..100)
    MAX-ACCESS 	read-write
    STATUS 	current
    DESCRIPTION 	"Digital audio mute duration threshold (in samples)."

    ::= { audioDisp 6 }


audOverLvl      OBJECT-TYPE
    SYNTAX 	INTEGER (-30..0)
    MAX-ACCESS 	read-write
    STATUS 	current
    DESCRIPTION 	"Digital audio threshold level for over-volume detection in dBFS."

    ::= { audioDisp 7 }


audOverTm       OBJECT-TYPE
    SYNTAX 	INTEGER (0..30)
    MAX-ACCESS 	read-write
    STATUS 	current
    DESCRIPTION 	"Digital audio over volume duration threshold (in seconds)."

    ::= { audioDisp 8 }


audSilenceLvl   OBJECT-TYPE
    SYNTAX 	INTEGER (-70..-40)
    MAX-ACCESS 	read-write
    STATUS 	current
    DESCRIPTION 	"Digital audio silence level in dBFS."

    ::= { audioDisp 9 }


audSilenceTm    OBJECT-TYPE
    SYNTAX 	INTEGER (0..60)
    MAX-ACCESS 	read-write
    STATUS 	current
    DESCRIPTION 	"Digital audio silence duration threshold (in seconds)."

    ::= { audioDisp 10 }


audProgLvl      OBJECT-TYPE
    SYNTAX 	INTEGER (-31..0)
    MAX-ACCESS 	read-write
    STATUS 	current
    DESCRIPTION 	"Digital audio peak program level in dBFS"

    ::= { audioDisp 11 }


audTestLvl      OBJECT-TYPE
    SYNTAX 	INTEGER (-31..0)
    MAX-ACCESS 	read-write
    STATUS 	current
    DESCRIPTION 	"Digital audio test level in dBFS"

    ::= { audioDisp 12 }


audCorrMtrSpd   OBJECT-TYPE
    SYNTAX 	INTEGER (1..20)
    MAX-ACCESS 	read-write
    STATUS 	current
    DESCRIPTION 	"Digital audio correlation meter speed."

    ::= { audioDisp 13 }


audAesActBits   OBJECT-TYPE
    SYNTAX 	INTEGER
    MAX-ACCESS 	read-only
    STATUS 	current
    DESCRIPTION 	"Active bits in the audio input stream as reported in theAES status block."

    ::= { audioDisp 14 }


audZeroDbMark   OBJECT-TYPE
    SYNTAX 	INTEGER {
        dBFS(0),
        peak-level(1),
        test-level(2)
    }
    MAX-ACCESS 	read-write
    STATUS 	current
    DESCRIPTION 	"Selects zero dB reference level for digital audio."

    ::= { audioDisp 15 }


audMeterNum     OBJECT-TYPE
    SYNTAX 	INTEGER (0..15)
    MAX-ACCESS 	not-accessible
    STATUS 	current
    DESCRIPTION 	"Audio level meter number for digital audio level meter table."

    ::= { audioDisp 16 }


audLevel        OBJECT-TYPE
    SYNTAX 	AudioLevel
    MAX-ACCESS 	read-only
    STATUS 	current
    DESCRIPTION 	"Current audio level of a digital audio input stream in dBFS (x 100), Analog input stream in dBU."

    ::= { audLvlEntry 1 }


audClipCount    OBJECT-TYPE
    SYNTAX 	INTEGER
    MAX-ACCESS 	read-only
    STATUS 	current
    DESCRIPTION 	"Current clip count for a digital audio stream in current session."

    ::= { audLvlEntry 2 }


audMuteCount    OBJECT-TYPE
    SYNTAX 	INTEGER
    MAX-ACCESS 	read-only
    STATUS 	current
    DESCRIPTION 	"Current mute count for a digital audio stream in current session."

    ::= { audLvlEntry 3 }


audActBits      OBJECT-TYPE
    SYNTAX 	INTEGER
    MAX-ACCESS 	read-only
    STATUS 	current
    DESCRIPTION 	"Active bits detected in an AES input stream."

    ::= { audLvlEntry 4 }


audSampleRt     OBJECT-TYPE
    SYNTAX 	INTEGER
    MAX-ACCESS 	read-only
    STATUS 	current
    DESCRIPTION 	"Sample rate of an AES input stream, Hz."

    ::= { audLvlEntry 5 }


audSilenceCount OBJECT-TYPE
    SYNTAX 	INTEGER
    MAX-ACCESS 	read-only
    STATUS 	current
    DESCRIPTION 	"Number of digital silence events detected in the current session."

    ::= { audLvlEntry 6 }


audOverCount    OBJECT-TYPE
    SYNTAX 	INTEGER
    MAX-ACCESS 	read-only
    STATUS 	current
    DESCRIPTION 	"Number of digital over events detected in the current session."

    ::= { audLvlEntry 7 }


audPeakLvl      OBJECT-TYPE
    SYNTAX 	AudioLevel
    MAX-ACCESS 	read-only
    STATUS 	current
    DESCRIPTION 	"Peak level in an audio channel."

    ::= { audLvlEntry 8 }


audSessionPeak  OBJECT-TYPE
    SYNTAX 	AudioLevel
    MAX-ACCESS 	read-only
    STATUS 	current
    DESCRIPTION 	"The Peak audio signal level measured by the signal level meter since the audio session was reset."

    ::= { audLvlEntry 9 }


audSessionHighLvl OBJECT-TYPE
    SYNTAX 	AudioLevel
    MAX-ACCESS 	read-only
    STATUS 	current
    DESCRIPTION 	"The highest audio signal level measured by the signal level meters."

    ::= { audLvlEntry 10 }


audLeqAvg       OBJECT-TYPE
    SYNTAX 	AudioLevel
    MAX-ACCESS 	read-only
    STATUS 	current
    DESCRIPTION 	"10 second moving average Channel Loudness."

    ::= { audLvlEntry 11 }


audLeqSession   OBJECT-TYPE
    SYNTAX 	AudioLevel
    MAX-ACCESS 	read-only
    STATUS 	current
    DESCRIPTION 	"Session controlled Channel Loudness, user defined averaging by session reset."

    ::= { audLvlEntry 12 }


audCurLoudness  OBJECT-TYPE
    SYNTAX 	AudioLevel
    MAX-ACCESS 	read-only
    STATUS 	current
    DESCRIPTION 	"Immediate Channel Loudness, no averaging applied."

    ::= { audLvlEntry 13 }


audLeqPairAvg   OBJECT-TYPE
    SYNTAX 	AudioLevel
    MAX-ACCESS 	read-only
    STATUS 	current
    DESCRIPTION 	"Average pair Loudness, 10 second moving average,note channel 1 and 2 (same pair), both report same value,same for 3&4 etc."

    ::= { audLvlEntry 14 }


audLeqPairSession OBJECT-TYPE
    SYNTAX 	AudioLevel
    MAX-ACCESS 	read-only
    STATUS 	current
    DESCRIPTION 	"Session pair Loudness, 10 second moving average,note channel 1 and 2 (same pair), both report same value,same for 3&4 etc."

    ::= { audLvlEntry 15 }


audPairCurLoudness OBJECT-TYPE
    SYNTAX 	AudioLevel
    MAX-ACCESS 	read-only
    STATUS 	current
    DESCRIPTION 	"Immediate pair Loudness, 10 second moving average,note channel 1 and 2 (same pair), both report same value,same for 3&4 etc."

    ::= { audLvlEntry 16 }


audLvlTable     OBJECT-TYPE
    SYNTAX 	SEQUENCE OF AudLvlEntry
    MAX-ACCESS 	not-accessible
    STATUS 	current
    DESCRIPTION 	"Table of digital audio statistics for each audio channel that isassociated with a level meter"

    ::= { audioDisp 17 }


audLvlEntry     OBJECT-TYPE
    SYNTAX 	AudLvlEntry
    MAX-ACCESS 	not-accessible
    STATUS 	current
    DESCRIPTION 	"A row in the audio level table "
    INDEX { audMeterNum }

    ::= { audLvlTable 1 }


AudLvlEntry ::= SEQUENCE {
    audLevel 	AudioLevel,
    audClipCount 	INTEGER,
    audMuteCount 	INTEGER,
    audActBits 	INTEGER,
    audSampleRt 	INTEGER,
    audSilenceCount 	INTEGER,
    audOverCount 	INTEGER,
    audPeakLvl 	AudioLevel,
    audSessionPeak 	AudioLevel,
    audSessionHighLvl 	AudioLevel,
    audLeqAvg 	AudioLevel,
    audLeqSession 	AudioLevel,
    audCurLoudness 	AudioLevel,
    audLeqPairAvg 	AudioLevel,
    audLeqPairSession 	AudioLevel,
    audPairCurLoudness 	AudioLevel 
}

audIgnoreValidBit OBJECT-TYPE
    SYNTAX 	INTEGER {
        off(0),
        on(1)
    }
    MAX-ACCESS 	read-write
    STATUS 	current
    DESCRIPTION 	"Enable/disable detection of valid bit in AES status block."

    ::= { audioDisp 18 }


audPkHoldSeg    OBJECT-TYPE
    SYNTAX 	INTEGER {
        off(0),
        on(1)
    }
    MAX-ACCESS 	read-write
    STATUS 	current
    DESCRIPTION 	"Enable/disable digital audio peak held segment."

    ::= { audioDisp 19 }


audLvlMtrScale  OBJECT-TYPE
    SYNTAX 	INTEGER {
        normal(0),
        custom(1)
    }
    MAX-ACCESS 	read-write
    STATUS 	current
    DESCRIPTION 	"On GET, indicates whether digital audio level meter scale isusing normal or custom values for height,offset and graticule step size. Setting the value to normal(0) resets digital audio meterscale parameters to normal values."

    ::= { audioDisp 20 }


audLvlMtrHeight OBJECT-TYPE
    SYNTAX 	INTEGER (10..90)
    MAX-ACCESS 	read-write
    STATUS 	current
    DESCRIPTION 	"Range of scale for custom digital audio meter configuration in dB."

    ::= { audioDisp 21 }


audLvlMtrOffset OBJECT-TYPE
    SYNTAX 	INTEGER (-30..0)
    MAX-ACCESS 	read-write
    STATUS 	current
    DESCRIPTION 	"Top of scale for custom digital audio meter configuration in dBFS."

    ::= { audioDisp 22 }


audLissAGC      OBJECT-TYPE
    SYNTAX 	INTEGER {
        off(0),
        on(1)
    }
    MAX-ACCESS 	read-write
    STATUS 	current
    DESCRIPTION 	"Enable/disable lissajous automatic gain control for digital audio."

    ::= { audioDisp 23 }


audSessionCtrl  OBJECT-TYPE
    SYNTAX 	INTEGER {
        reset(0),
        stop(1),
        run(2)
    }
    MAX-ACCESS 	read-write
    STATUS 	current
    DESCRIPTION 	"Audio sesssion control. To use in SIM mode, select channel with selectTile command."

    ::= { audioDisp 24 }


audGratStepSize OBJECT-TYPE
    SYNTAX 	INTEGER (3..10)
    MAX-ACCESS 	read-write
    STATUS 	current
    DESCRIPTION 	"Graticule step size for custom digital audio meter scale configuration in dB."

    ::= { audioDisp 25 }


audConfigAesBnc OBJECT-TYPE
    SYNTAX 	INTEGER {
        input(0),
        output(1)
    }
    MAX-ACCESS 	read-write
    STATUS 	current
    DESCRIPTION 	"Configure the AES BNC's as outputs or inputs."

    ::= { audioDisp 26 }


audDominanceSound OBJECT-TYPE
    SYNTAX 	INTEGER {
        disable(0),
        enable(1)
    }
    MAX-ACCESS 	read-write
    STATUS 	current
    DESCRIPTION 	"Enable/Disable audio surround dominance sound indicator."

    ::= { audioDisp 27 }


audWeightingFilter OBJECT-TYPE
    SYNTAX 	INTEGER {
        linear(0),
        a-weighting(1),
        rlb-weighting(2)
    }
    MAX-ACCESS 	read-write
    STATUS 	current
    DESCRIPTION 	"Select audio weighting filter for surround sound display."

    ::= { audioDisp 28 }


audSessionRuntime OBJECT-TYPE
    SYNTAX 	DisplayString
    MAX-ACCESS 	read-only
    STATUS 	current
    DESCRIPTION 	"Audio session run time."

    ::= { audioDisp 29 }


dolbyFormatDetected OBJECT-TYPE
    SYNTAX 	DisplayString
    MAX-ACCESS 	read-only
    STATUS 	current
    DESCRIPTION 	"Detected dolby format."

    ::= { audioDisp 30 }


dolbySampleRate OBJECT-TYPE
    SYNTAX 	INTEGER
    MAX-ACCESS 	read-only
    STATUS 	current
    DESCRIPTION 	"Dolby sample rate in sample/second."

    ::= { audioDisp 31 }


dolbyEFrameRate OBJECT-TYPE
    SYNTAX 	DisplayString
    MAX-ACCESS 	read-only
    STATUS 	current
    DESCRIPTION 	"Dolby E Frame rate."

    ::= { audioDisp 32 }


dolbySource     OBJECT-TYPE
    SYNTAX 	INTEGER {
        notDolby(0),
         aesA1-2(11),
         aesA3-4(12),
         aesA5-6(13),
         aesA7-8(14),
         aesB1-2(21),
         aesB3-4(22),
         aesB5-6(23),
         aesB7-8(24),
         emb1-2(101),
         emb3-4(102),
         emb5-6(103),
         emb7-8(104),
         emb9-10(105),
         emb11-12(106),
         emb13-14(107),
         emb15-16(108)
    }
    MAX-ACCESS 	read-only
    STATUS 	current
    DESCRIPTION 	"Dolby Input Source Selection. Gives which source goes to the dolby decoder."

    ::= { audioDisp 33 }


dolbyTimecode   OBJECT-TYPE
    SYNTAX 	DisplayString
    MAX-ACCESS 	read-only
    STATUS 	current
    DESCRIPTION 	"Dolby Timecode."

    ::= { audioDisp 34 }


dolbyProgram    OBJECT-TYPE
    SYNTAX 	INTEGER {
        prog1(0),
        prog2(1),
        prog3(2),
        prog4(3),
        prog5(4),
        prog6(5),
        prog7(6),
        prog8(7)
    }
    MAX-ACCESS 	not-accessible
    STATUS 	current
    DESCRIPTION 	"Dolby E Program.  This is used as index in dolbyMetadataTable."

    ::= { audioDisp 35 }


dolbyProgramConfig OBJECT-TYPE
    SYNTAX 	INTEGER {
        none(0),
        progCfg1(1),
        progCfg2(2),
        progCfg4(3),
        progCfg5-1(4),
        progCfg7-1(5)
    }
    MAX-ACCESS 	read-only
    STATUS 	current
    DESCRIPTION 	" Dolby program configuration."

    ::= { dolbyInputStatusEntry 1 }


dolbyProgDesc   OBJECT-TYPE
    SYNTAX 	DisplayString
    MAX-ACCESS 	read-only
    STATUS 	current
    DESCRIPTION 	"Program description text."

    ::= { dolbyInputStatusEntry 2 }


dolbyChannelMode OBJECT-TYPE
    SYNTAX 	INTEGER {
        none(0),
        dual-mono(1),
        channelMode1-0(2),
        channelMode2-0(3),
        channelMode3-0(4),
        channelMode2-1(5),
        channelMode3-1(6),
        channelMode2-2(7),
        channelMode3-2(8)
    }
    MAX-ACCESS 	read-only
    STATUS 	current
    DESCRIPTION 	" Dolby channel mode."

    ::= { dolbyInputStatusEntry 3 }


dolbyLFEChannel OBJECT-TYPE
    SYNTAX 	INTEGER {
        absent(0),
        present(1)
    }
    MAX-ACCESS 	read-only
    STATUS 	current
    DESCRIPTION 	" Dolby LFE channel presence."

    ::= { dolbyInputStatusEntry 4 }


dolbyDialogLevel OBJECT-TYPE
    SYNTAX 	AudioLevel
    MAX-ACCESS 	read-only
    STATUS 	current
    DESCRIPTION 	"Dolby Dialog level."

    ::= { dolbyInputStatusEntry 5 }


dolbyLineModeProfile OBJECT-TYPE
    SYNTAX 	INTEGER {
        none(0),
        filmLight(1),
        filmStd(2),
        musicLight(3),
        musicStd(4),
        speech(5)
    }
    MAX-ACCESS 	read-only
    STATUS 	current
    DESCRIPTION 	"Amount of dynamic range compression."

    ::= { dolbyInputStatusEntry 6 }


dolbyLineModeCmpr OBJECT-TYPE
    SYNTAX 	AudioLevel
    MAX-ACCESS 	read-only
    STATUS 	current
    DESCRIPTION 	"Line mode compression profile."

    ::= { dolbyInputStatusEntry 7 }


dolbyRFModeProfile OBJECT-TYPE
    SYNTAX 	INTEGER {
        none(0),
        filmLight(1),
        filmStd(2),
        musicLight(3),
        musicStd(4),
        speech(5)
    }
    MAX-ACCESS 	read-only
    STATUS 	current
    DESCRIPTION 	"Amount of dynamic range compression."

    ::= { dolbyInputStatusEntry 8 }


dolbyRFModeCmpr OBJECT-TYPE
    SYNTAX 	AudioLevel
    MAX-ACCESS 	read-only
    STATUS 	current
    DESCRIPTION 	"RF mode compression profile"

    ::= { dolbyInputStatusEntry 9 }


dolbyBitstreamMode OBJECT-TYPE
    SYNTAX 	INTEGER {
        none(0),
        cm(1),
        me(2),
        vi(3),
        hi(4),
        d(5),
        c(6),
        e(7),
        vo(8),
        k(9)
    }
    MAX-ACCESS 	read-only
    STATUS 	current
    DESCRIPTION 	" Bit stream mode."

    ::= { dolbyInputStatusEntry 10 }


dolbyRFOvermodProt OBJECT-TYPE
    SYNTAX 	INTEGER {
        disabled(0),
        enabled(1)
    }
    MAX-ACCESS 	read-only
    STATUS 	current
    DESCRIPTION 	" RF overmodulation protection."

    ::= { dolbyInputStatusEntry 11 }


dolbyCenterDownmixLvl OBJECT-TYPE
    SYNTAX 	AudioLevel
    MAX-ACCESS 	read-only
    STATUS 	current
    DESCRIPTION 	"Center downmix level"

    ::= { dolbyInputStatusEntry 12 }


dolbySurDownmixLvl OBJECT-TYPE
    SYNTAX 	AudioLevel
    MAX-ACCESS 	read-only
    STATUS 	current
    DESCRIPTION 	"Surround downmix level"

    ::= { dolbyInputStatusEntry 13 }


dolbySurMode    OBJECT-TYPE
    SYNTAX 	INTEGER {
        no(0),
        yes(1),
        not-indicated(2)
    }
    MAX-ACCESS 	read-only
    STATUS 	current
    DESCRIPTION 	" Dolby surround mode."

    ::= { dolbyInputStatusEntry 14 }


dolbyAudioProdnInfo OBJECT-TYPE
    SYNTAX 	INTEGER {
        absent(0),
        present(1)
    }
    MAX-ACCESS 	read-only
    STATUS 	current
    DESCRIPTION 	"Audio production information."

    ::= { dolbyInputStatusEntry 15 }


dolbyMixingLvl  OBJECT-TYPE
    SYNTAX 	INTEGER
    MAX-ACCESS 	read-only
    STATUS 	current
    DESCRIPTION 	"Mixing Level. 0 dB when not indicated."

    ::= { dolbyInputStatusEntry 16 }


dolbyRoomType   OBJECT-TYPE
    SYNTAX 	INTEGER {
        not-indicated(0),
        small(1),
        large(2)
    }
    MAX-ACCESS 	read-only
    STATUS 	current
    DESCRIPTION 	"Room type."

    ::= { dolbyInputStatusEntry 17 }


dolbyCopyrightBit OBJECT-TYPE
    SYNTAX 	INTEGER {
        no(0),
        yes(1)
    }
    MAX-ACCESS 	read-only
    STATUS 	current
    DESCRIPTION 	"Copyright bit."

    ::= { dolbyInputStatusEntry 18 }


dolbyBitstreamOriginal OBJECT-TYPE
    SYNTAX 	INTEGER {
        no(0),
        yes(1)
    }
    MAX-ACCESS 	read-only
    STATUS 	current
    DESCRIPTION 	"Original bitstream."

    ::= { dolbyInputStatusEntry 19 }


dolbyExtendedBSI OBJECT-TYPE
    SYNTAX 	INTEGER {
        absent(0),
        present(1)
    }
    MAX-ACCESS 	read-only
    STATUS 	current
    DESCRIPTION 	"dolby extended BSI."

    ::= { dolbyInputStatusEntry 20 }


dolbyStereoDmixPref OBJECT-TYPE
    SYNTAX 	INTEGER {
        not-indicated(0),
        loro(1),
        ltrt(2)
    }
    MAX-ACCESS 	read-only
    STATUS 	current
    DESCRIPTION 	"Preferred stereo downmix mode."

    ::= { dolbyInputStatusEntry 21 }


dolbyLt-RtCenterMixLvl OBJECT-TYPE
    SYNTAX 	AudioLevel
    MAX-ACCESS 	read-only
    STATUS 	current
    DESCRIPTION 	"Lt/Rt Center Downmix level"

    ::= { dolbyInputStatusEntry 22 }


dolbyLt-RtSurDmixLvl OBJECT-TYPE
    SYNTAX 	AudioLevel
    MAX-ACCESS 	read-only
    STATUS 	current
    DESCRIPTION 	"Lt/Rt Surround Downmix level"

    ::= { dolbyInputStatusEntry 23 }


dolbyLo-RoCenterDmixLvl OBJECT-TYPE
    SYNTAX 	AudioLevel
    MAX-ACCESS 	read-only
    STATUS 	current
    DESCRIPTION 	"Lo/Ro Center Downmix level"

    ::= { dolbyInputStatusEntry 24 }


dolbyLo-RoSurDMixLvl OBJECT-TYPE
    SYNTAX 	AudioLevel
    MAX-ACCESS 	read-only
    STATUS 	current
    DESCRIPTION 	"Lo/Ro Surround Downmix level"

    ::= { dolbyInputStatusEntry 25 }


dolbySurEXMode  OBJECT-TYPE
    SYNTAX 	INTEGER {
        no(0),
        yes(1),
        not-indicated(2)
    }
    MAX-ACCESS 	read-only
    STATUS 	current
    DESCRIPTION 	"Surround EX Mode."

    ::= { dolbyInputStatusEntry 26 }


dolbyA-DConverterType OBJECT-TYPE
    SYNTAX 	INTEGER {
        standard(0),
        hdcd(1)
    }
    MAX-ACCESS 	read-only
    STATUS 	current
    DESCRIPTION 	"A/D converter type"

    ::= { dolbyInputStatusEntry 27 }


dolbyDCFilter   OBJECT-TYPE
    SYNTAX 	INTEGER {
        no(0),
        yes(1)
    }
    MAX-ACCESS 	read-only
    STATUS 	current
    DESCRIPTION 	"DC Filter."

    ::= { dolbyInputStatusEntry 28 }


dolbyLowpassFilter OBJECT-TYPE
    SYNTAX 	INTEGER {
        no(0),
        yes(1)
    }
    MAX-ACCESS 	read-only
    STATUS 	current
    DESCRIPTION 	"Lowpass Filter."

    ::= { dolbyInputStatusEntry 29 }


dolbyLFELowpassFilter OBJECT-TYPE
    SYNTAX 	INTEGER {
        no(0),
        yes(1)
    }
    MAX-ACCESS 	read-only
    STATUS 	current
    DESCRIPTION 	"LFE Lowpass  Filter."

    ::= { dolbyInputStatusEntry 30 }


dolbySur3dBAtten OBJECT-TYPE
    SYNTAX 	INTEGER {
        no(0),
        yes(1)
    }
    MAX-ACCESS 	read-only
    STATUS 	current
    DESCRIPTION 	"Surround 3 dB Attenuation."

    ::= { dolbyInputStatusEntry 31 }


dolbySurPhaseShift OBJECT-TYPE
    SYNTAX 	INTEGER {
        no(0),
        yes(1)
    }
    MAX-ACCESS 	read-only
    STATUS 	current
    DESCRIPTION 	"Surround phase shift."

    ::= { dolbyInputStatusEntry 32 }


dolbyHeadphoneMode OBJECT-TYPE
    SYNTAX 	INTEGER {
        no(0),
        yes(1),
        not-indicated(2)
    }
    MAX-ACCESS 	read-only
    STATUS 	current
    DESCRIPTION 	"Surround EX Mode."

    ::= { dolbyInputStatusEntry 33 }


dolbyDataRate   OBJECT-TYPE
    SYNTAX 	INTEGER
    MAX-ACCESS 	read-only
    STATUS 	current
    DESCRIPTION 	"Dolby Data rate in kb/s. 0 when not indicated."

    ::= { dolbyInputStatusEntry 34 }


dolbyPgmAvg     OBJECT-TYPE
    SYNTAX 	AudioLevel
    MAX-ACCESS 	read-only
    STATUS 	current
    DESCRIPTION 	"Average Program Loudness, variable integration time."

    ::= { dolbyInputStatusEntry 35 }


dolbyPgmCurLoudness OBJECT-TYPE
    SYNTAX 	AudioLevel
    MAX-ACCESS 	read-only
    STATUS 	current
    DESCRIPTION 	"Immediate Program Loudness, short integration time."

    ::= { dolbyInputStatusEntry 36 }


dolbyPgmSessionLoudness OBJECT-TYPE
    SYNTAX 	AudioLevel
    MAX-ACCESS 	read-only
    STATUS 	current
    DESCRIPTION 	"Session controlled Program Loudness, user defined averaging controled by session reset"

    ::= { dolbyInputStatusEntry 37 }


dolbyEFrameLoc  OBJECT-TYPE
    SYNTAX 	DisplayString
    MAX-ACCESS 	read-only
    STATUS 	current
    DESCRIPTION 	"Dolby E Frame location."

    ::= { dolbyInputStatusEntry 38 }


dolbyMetadataTable OBJECT-TYPE
    SYNTAX 	SEQUENCE OF DolbyInputStatusEntry
    MAX-ACCESS 	not-accessible
    STATUS 	current
    DESCRIPTION 	"Table for dolby metadata status"

    ::= { audioDisp 36 }


dolbyInputStatusEntry OBJECT-TYPE
    SYNTAX 	DolbyInputStatusEntry
    MAX-ACCESS 	not-accessible
    STATUS 	current
    DESCRIPTION 	"A row in the Dolby Metadata Table "
    INDEX { dolbyProgram }

    ::= { dolbyMetadataTable 1 }


DolbyInputStatusEntry ::= SEQUENCE {
    dolbyProgramConfig 	INTEGER,
    dolbyProgDesc 	DisplayString,
    dolbyChannelMode 	INTEGER,
    dolbyLFEChannel 	INTEGER,
    dolbyDialogLevel 	AudioLevel,
    dolbyLineModeProfile 	INTEGER,
    dolbyLineModeCmpr 	AudioLevel,
    dolbyRFModeProfile 	INTEGER,
    dolbyRFModeCmpr 	AudioLevel,
    dolbyBitstreamMode 	INTEGER,
    dolbyRFOvermodProt 	INTEGER,
    dolbyCenterDownmixLvl 	AudioLevel,
    dolbySurDownmixLvl 	AudioLevel,
    dolbySurMode 	INTEGER,
    dolbyAudioProdnInfo 	INTEGER,
    dolbyMixingLvl 	INTEGER,
    dolbyRoomType 	INTEGER,
    dolbyCopyrightBit 	INTEGER,
    dolbyBitstreamOriginal 	INTEGER,
    dolbyExtendedBSI 	INTEGER,
    dolbyStereoDmixPref 	INTEGER,
    dolbyLt-RtCenterMixLvl 	AudioLevel,
    dolbyLt-RtSurDmixLvl 	AudioLevel,
    dolbyLo-RoCenterDmixLvl 	AudioLevel,
    dolbyLo-RoSurDMixLvl 	AudioLevel,
    dolbySurEXMode 	INTEGER,
    dolbyA-DConverterType 	INTEGER,
    dolbyDCFilter 	INTEGER,
    dolbyLowpassFilter 	INTEGER,
    dolbyLFELowpassFilter 	INTEGER,
    dolbySur3dBAtten 	INTEGER,
    dolbySurPhaseShift 	INTEGER,
    dolbyHeadphoneMode 	INTEGER,
    dolbyDataRate 	INTEGER,
    dolbyPgmAvg 	AudioLevel,
    dolbyPgmCurLoudness 	AudioLevel,
    dolbyPgmSessionLoudness 	AudioLevel,
    dolbyEFrameLoc 	DisplayString 
}

audAesCurOutput OBJECT-TYPE
    SYNTAX 	DisplayString
    MAX-ACCESS 	read-only
    STATUS 	current
    DESCRIPTION 	"Currently selected AES outputs."

    ::= { audioDisp 37 }

-- dep-dolbyDataRate  (audioDisp, 38)

audMeterType    OBJECT-TYPE
    SYNTAX 	INTEGER {
        dbfs(0),
        din(1),
        nordic(2),
        vu(3),
        ieee(4),
        bbc(5),
        bbcm(6)
    }
    MAX-ACCESS 	read-write
    STATUS 	current
    DESCRIPTION 	"Digital audio meter presets for standard audio meter configurations."

    ::= { audioDisp 39 }


audDigChanLoudThreshold OBJECT-TYPE
    SYNTAX 	INTEGER (-30..0)
    MAX-ACCESS 	read-write
    STATUS 	current
    DESCRIPTION 	"Digital Audio Channel Loudness threshold for Audio."

    ::= { audioDisp 40 }


audDigPgmLoudThreshold OBJECT-TYPE
    SYNTAX 	INTEGER (-30..0)
    MAX-ACCESS 	read-write
    STATUS 	current
    DESCRIPTION 	"Digital Audio Program Loudness threshold for Audio."

    ::= { audioDisp 41 }


avDelayEnable   OBJECT-TYPE
    SYNTAX 	INTEGER {
        off(0),
        on(1)
    }
    MAX-ACCESS 	read-write
    STATUS 	current
    DESCRIPTION 	"Display AV Delay value in AV Delay status."

    ::= { audioDisp 42 }


avDelayValue    OBJECT-TYPE
    SYNTAX 	INTEGER
    MAX-ACCESS 	read-only
    STATUS 	current
    DESCRIPTION 	"Current AV Delay value in mS."

    ::= { audioDisp 43 }


channelNum      OBJECT-TYPE
    SYNTAX 	INTEGER {
        channel1(0),
        channel2(1),
        channel3(2),
        channel4(3),
        channel5(4),
        channel6(5),
        channel7(6),
        channel8(7)
    }
    MAX-ACCESS 	not-accessible
    STATUS 	current
    DESCRIPTION 	"Audio channel number.  This is used as index in the channel status info table(channelStatusInfoTable)."

    ::= { audioDisp 44 }


chanStatusPair  OBJECT-TYPE
    SYNTAX 	INTEGER {
        pair1-2(0),
        pair3-4(1),
        pair5-6(2),
        pair7-8(3)
    }
    MAX-ACCESS 	read-write
    STATUS 	current
    DESCRIPTION 	"Selects channel pair for channel status display for current tile."

    ::= { channelStatusEntry 1 }


chanStatusFmt   OBJECT-TYPE
    SYNTAX 	INTEGER {
        text(0),
        hex(1),
        binary(2),
        xmsn-binary(3)
    }
    MAX-ACCESS 	read-write
    STATUS 	current
    DESCRIPTION 	"Selects channel status display format for current tile."

    ::= { channelStatusEntry 2 }


channelStatusTable OBJECT-TYPE
    SYNTAX 	SEQUENCE OF ChannelStatusEntry
    MAX-ACCESS 	not-accessible
    STATUS 	current
    DESCRIPTION 	"Table for channel status pair and format of data in the current tile."

    ::= { audioDisp 45 }


channelStatusEntry OBJECT-TYPE
    SYNTAX 	ChannelStatusEntry
    MAX-ACCESS 	not-accessible
    STATUS 	current
    DESCRIPTION 	"A row in the channelStatusTable"
    INDEX { currTile }

    ::= { channelStatusTable 1 }


ChannelStatusEntry ::= SEQUENCE {
    chanStatusPair 	INTEGER,
    chanStatusFmt 	INTEGER 
}

chanStatChanUse OBJECT-TYPE
    SYNTAX 	INTEGER {
        consumer(0),
        professional(1)
    }
    MAX-ACCESS 	read-write
    STATUS 	current
    DESCRIPTION 	"Channel usage mode."

    ::= { channelStatusInfoEntry 1 }


chanStatDataUse OBJECT-TYPE
    SYNTAX 	INTEGER {
        audio(0),
        non-audio(1)
    }
    MAX-ACCESS 	read-write
    STATUS 	current
    DESCRIPTION 	"Channel data type."

    ::= { channelStatusInfoEntry 2 }


chanStatEmphasis OBJECT-TYPE
    SYNTAX 	INTEGER {
        not-indicated(0),
        no-emphasis(1),
        emp-50-15-us(2),
        ccitt-J-17(3),
        unused(4)
    }
    MAX-ACCESS 	read-write
    STATUS 	current
    DESCRIPTION 	"Channel emphasis mode."

    ::= { channelStatusInfoEntry 3 }


chanStatLocked  OBJECT-TYPE
    SYNTAX 	INTEGER {
        locked(0),
        unlocked(1)
    }
    MAX-ACCESS 	read-write
    STATUS 	current
    DESCRIPTION 	"Channel locking status (locked/unlocked)."

    ::= { channelStatusInfoEntry 4 }


chanStatSampleFreq OBJECT-TYPE
    SYNTAX 	INTEGER {
        not-indicated(0),
        frq-22-05-kHz(1),
        frq-24-kHz(2),
        frq-32-kHz(3),
        frq-44-1-kHz(4),
        frq-48-kHz(5),
        frq-64-kHz(6),
        frq-88-2-kHz(7),
        frq-96-kHz(8),
        frq-176-4-kHz(9),
        frq-192-kHz(10),
        frq-352-8-kHz(11),
        frq-384-kHz(12),
        unused(13)
    }
    MAX-ACCESS 	read-write
    STATUS 	current
    DESCRIPTION 	"Channel sample frequency."

    ::= { channelStatusInfoEntry 5 }


chanStatChanMode OBJECT-TYPE
    SYNTAX 	INTEGER {
        not-indicated(0),
        one-channel-fq2-lf(1),
        stereo(2),
        monaural(3),
        user-defined(4),
        two-channel(5),
        one-channel-fq2-rt(6),
        pri-sec(7),
        one-channel-fq2(8),
        unused(9)
    }
    MAX-ACCESS 	read-write
    STATUS 	current
    DESCRIPTION 	"Channel encode mode."

    ::= { channelStatusInfoEntry 6 }


chanStatUserBitMode OBJECT-TYPE
    SYNTAX 	INTEGER {
        not-indicated(0),
        aes-18(1),
        mode-192-bit-blocks(2),
        user-defined(3),
        unused(4)
    }
    MAX-ACCESS 	read-write
    STATUS 	current
    DESCRIPTION 	"Channel user bit management mode."

    ::= { channelStatusInfoEntry 7 }


chanStatAuxBitUsage OBJECT-TYPE
    SYNTAX 	INTEGER {
        not-indicated(0),
        talk-back(1),
        main-audio(2),
        user-defined(3),
        unused(4)
    }
    MAX-ACCESS 	read-write
    STATUS 	current
    DESCRIPTION 	"Channel AUX bits usage."

    ::= { channelStatusInfoEntry 8 }


chanStatWordLen OBJECT-TYPE
    SYNTAX 	INTEGER {
        not-indicated(0),
        len-20-24-bits(1),
        len-22-24-bits(2),
        len-23-24-bits(3),
        len-24-24-bits(4),
        len-21-24-bits(5),
        len-16-20-bits(6),
        len-18-20-bits(7),
        len-19-20-bits(8),
        len-20-20-bits(9),
        len-17-20-bits(10),
        unused(11)
    }
    MAX-ACCESS 	read-write
    STATUS 	current
    DESCRIPTION 	"Channel audio word length."

    ::= { channelStatusInfoEntry 9 }


chanStatAlignLevel OBJECT-TYPE
    SYNTAX 	INTEGER {
        not-indicated(0),
        ebu-r68(1),
        smpte-rp155(2),
        unused(3)
    }
    MAX-ACCESS 	read-write
    STATUS 	current
    DESCRIPTION 	"Channel alignment level."

    ::= { channelStatusInfoEntry 10 }


chanStatRefSignal OBJECT-TYPE
    SYNTAX 	INTEGER {
        not-a-ref(0),
        grade-2-ref(1),
        grade-1-ref(2),
        unused(3)
    }
    MAX-ACCESS 	read-write
    STATUS 	current
    DESCRIPTION 	"Channel reference signal."

    ::= { channelStatusInfoEntry 11 }


chanStatOrigin  OBJECT-TYPE
    SYNTAX 	DisplayString
    MAX-ACCESS 	read-write
    STATUS 	current
    DESCRIPTION 	"Channel origin."

    ::= { channelStatusInfoEntry 12 }


chanStatDestination OBJECT-TYPE
    SYNTAX 	DisplayString
    MAX-ACCESS 	read-write
    STATUS 	current
    DESCRIPTION 	"Channel destination."

    ::= { channelStatusInfoEntry 13 }


chanStatTimeOfDay OBJECT-TYPE
    SYNTAX 	DisplayString
    MAX-ACCESS 	read-write
    STATUS 	current
    DESCRIPTION 	"Channel Time of day."

    ::= { channelStatusInfoEntry 14 }


chanStatSampleNum OBJECT-TYPE
    SYNTAX 	INTEGER
    MAX-ACCESS 	read-write
    STATUS 	current
    DESCRIPTION 	"Channel sample number."

    ::= { channelStatusInfoEntry 15 }


chanStatCrc     OBJECT-TYPE
    SYNTAX 	INTEGER
    MAX-ACCESS 	read-write
    STATUS 	current
    DESCRIPTION 	"Stored block CRC."

    ::= { channelStatusInfoEntry 16 }


chanStatCrcComputed OBJECT-TYPE
    SYNTAX 	INTEGER
    MAX-ACCESS 	read-write
    STATUS 	current
    DESCRIPTION 	"Computed block CRC."

    ::= { channelStatusInfoEntry 17 }


channelStatusInfoTable OBJECT-TYPE
    SYNTAX 	SEQUENCE OF ChannelStatusInfoEntry
    MAX-ACCESS 	not-accessible
    STATUS 	current
    DESCRIPTION 	"Table for channel status information(packet content) for the selected channel."

    ::= { audioDisp 46 }


channelStatusInfoEntry OBJECT-TYPE
    SYNTAX 	ChannelStatusInfoEntry
    MAX-ACCESS 	not-accessible
    STATUS 	current
    DESCRIPTION 	"A row in the channelStatusInfoTable"
    INDEX { channelNum }

    ::= { channelStatusInfoTable 1 }


ChannelStatusInfoEntry ::= SEQUENCE {
    chanStatChanUse 	INTEGER,
    chanStatDataUse 	INTEGER,
    chanStatEmphasis 	INTEGER,
    chanStatLocked 	INTEGER,
    chanStatSampleFreq 	INTEGER,
    chanStatChanMode 	INTEGER,
    chanStatUserBitMode 	INTEGER,
    chanStatAuxBitUsage 	INTEGER,
    chanStatWordLen 	INTEGER,
    chanStatAlignLevel 	INTEGER,
    chanStatRefSignal 	INTEGER,
    chanStatOrigin 	DisplayString,
    chanStatDestination 	DisplayString,
    chanStatTimeOfDay 	DisplayString,
    chanStatSampleNum 	INTEGER,
    chanStatCrc 	INTEGER,
    chanStatCrcComputed 	INTEGER 
}

dolbyMetadataSrc OBJECT-TYPE
    SYNTAX 	INTEGER {
        aes(0),
        vanc(1),
        auto(2)
    }
    MAX-ACCESS 	read-write
    STATUS 	current
    DESCRIPTION 	"Selects Dolby metadata source for current tile."

    ::= { dolbyVancEntry 1 }


dolbyVancSrc    OBJECT-TYPE
    SYNTAX 	INTEGER {
        unknown(0),
        emb1-2(1),
        emb3-4(2),
        emb5-6(3),
        emb7-8(4),
        emb9-10(5),
        emb11-12(6),
        emb13-14(7),
        emb15-16(8)
    }
    MAX-ACCESS 	read-write
    STATUS 	current
    DESCRIPTION 	"Selects Dolby VANC pair for current tile."

    ::= { dolbyVancEntry 2 }


dolbyVancDID    OBJECT-TYPE
    SYNTAX 	INTEGER {
        fortyFive(0),
        fifty(1)
    }
    MAX-ACCESS 	read-write
    STATUS 	current
    DESCRIPTION 	"Selects Dolby VANC DID for current tile."

    ::= { dolbyVancEntry 3 }


dolbyVancTable  OBJECT-TYPE
    SYNTAX 	SEQUENCE OF DolbyVancEntry
    MAX-ACCESS 	not-accessible
    STATUS 	current
    DESCRIPTION 	"Table for Dolby VANC metadata"

    ::= { audioDisp 47 }


dolbyVancEntry  OBJECT-TYPE
    SYNTAX 	DolbyVancEntry
    MAX-ACCESS 	not-accessible
    STATUS 	current
    DESCRIPTION 	"A row in the dolbyVancTable"
    INDEX { currTile }

    ::= { dolbyVancTable 1 }


DolbyVancEntry ::= SEQUENCE {
    dolbyMetadataSrc 	INTEGER,
    dolbyVancSrc 	INTEGER,
    dolbyVancDID 	INTEGER 
}

avDelayOffset   OBJECT-TYPE
    SYNTAX 	INTEGER
    MAX-ACCESS 	read-write
    STATUS 	current
    DESCRIPTION 	"AV Delay manual offset in mS. Use -1 to save the current av delay as offset."

    ::= { audioDisp 48 }


audEmb16ChBallistics OBJECT-TYPE
    SYNTAX 	INTEGER {
        truePeak(0),
        ppm1(1),
        ppm2(2)
    }
    MAX-ACCESS 	read-write
    STATUS 	current
    DESCRIPTION 	"Level Meter ballistics selection for 16 channel embedded audio."

    ::= { audioDisp 49 }


audLoudnessBallistic OBJECT-TYPE
    SYNTAX 	INTEGER {
        iec62672f(6),
        ebuR128m(7),
        iec62672s(8),
        shortAve(9),
        unGatedLong(10),
        longAve(11)
    }
    MAX-ACCESS 	read-write
    STATUS 	current
    DESCRIPTION 	"Selection for Digital Audio Loudness Ballistic"

    ::= { audioDisp 50 }


audLoudnessMeterStyle OBJECT-TYPE
    SYNTAX 	INTEGER {
        threeColor(0),
        bs1771(1),
        fiveColor(2)
    }
    MAX-ACCESS 	not-accessible
    STATUS 	current
    DESCRIPTION 	"Not Used "

    ::= { audioDisp 51 }


audLoudMtrScale OBJECT-TYPE
    SYNTAX 	INTEGER {
        normal(0),
        custom(1)
    }
    MAX-ACCESS 	read-write
    STATUS 	current
    DESCRIPTION 	" On GET, indicates whether Loudnes Meter Scale is using normal or custom values for scale. Setting value to zero resets meter to normal."

    ::= { audioDisp 52 }


audLoudMtrHeight OBJECT-TYPE
    SYNTAX 	INTEGER (10..90)
    MAX-ACCESS 	read-write
    STATUS 	current
    DESCRIPTION 	"Range of scale for custom loudness meter Configuration in dB."

    ::= { audioDisp 53 }


audLoudMtrOffset OBJECT-TYPE
    SYNTAX 	INTEGER (-30..0)
    MAX-ACCESS 	read-write
    STATUS 	current
    DESCRIPTION 	"Top of scale for custom loudness meter configuration in dB."

    ::= { audioDisp 54 }


audLoudMtrGratStepSize OBJECT-TYPE
    SYNTAX 	INTEGER (3..10)
    MAX-ACCESS 	read-write
    STATUS 	current
    DESCRIPTION 	"Graticule step size for custom loudness meter scale configuration in dB."

    ::= { audioDisp 55 }


audDigPgmQuiteThreshold OBJECT-TYPE
    SYNTAX 	INTEGER (-60..0)
    MAX-ACCESS 	read-write
    STATUS 	current
    DESCRIPTION 	"Audio Program Loudness Quiet Threshold."

    ::= { audioDisp 56 }


audDigDNDeltaThreshold OBJECT-TYPE
    SYNTAX 	INTEGER (0..10)
    MAX-ACCESS 	read-write
    STATUS 	current
    DESCRIPTION 	"Target DialNorm Delta for Loudness."

    ::= { audioDisp 57 }


audPhaseErrThr  OBJECT-TYPE
    SYNTAX 	INTEGER (-100..-1)
    MAX-ACCESS 	read-write
    STATUS 	current
    DESCRIPTION 	"Digital audio correlation threshold for audio phase error in percent."

    ::= { audioDisp 58 }


audPhaseErrTime OBJECT-TYPE
    SYNTAX 	INTEGER (0..30)
    MAX-ACCESS 	read-write
    STATUS 	current
    DESCRIPTION 	"Digital audio phase error duration threshold (in seconds)."

    ::= { audioDisp 59 }


avDelayPropagationValue OBJECT-TYPE
    SYNTAX 	INTEGER
    MAX-ACCESS 	read-only
    STATUS 	current
    DESCRIPTION 	"Current AV Delay propagation value in mS."

    ::= { audioDisp 60 }

-- 
-- wfm group
-- Waveform display mode variables

wfmMode         OBJECT-TYPE
    SYNTAX 	INTEGER {
        parade(0),
        overlay(1)
    }
    MAX-ACCESS 	read-write
    STATUS 	current
    DESCRIPTION 	"Waveform sweep display mode."

    ::= { wfmEntry 1 }


wfmFilterCpst   OBJECT-TYPE
    SYNTAX 	INTEGER {
        flat(0),
        luma(1),
        chroma(2),
        flat-luma(3)
    }
    MAX-ACCESS 	read-write
    STATUS 	current
    DESCRIPTION 	"Waveform filter for Composite display mode."

    ::= { wfmEntry 2 }


wfmFilterYcbcr  OBJECT-TYPE
    SYNTAX 	INTEGER {
        flat(0),
        lowpass(1)
    }
    MAX-ACCESS 	read-write
    STATUS 	current
    DESCRIPTION 	"Waveform filter for YCbCr display mode."

    ::= { wfmEntry 3 }


wfmFilterRgb    OBJECT-TYPE
    SYNTAX 	INTEGER {
        flat(0),
        lowpass(1)
    }
    MAX-ACCESS 	read-write
    STATUS 	current
    DESCRIPTION 	"Waveform filter for RGB display mode."

    ::= { wfmEntry 4 }


wfmFilterYrgb   OBJECT-TYPE
    SYNTAX 	INTEGER {
        flat(0),
        lowpass(1)
    }
    MAX-ACCESS 	read-write
    STATUS 	current
    DESCRIPTION 	"Waveform filter for YRGB display mode."

    ::= { wfmEntry 5 }


wfmColorSpace   OBJECT-TYPE
    SYNTAX 	INTEGER {
        none(0),
        composite(1),
        ycbcr(2),
        rgb(3),
        yrgb(4),
        xyz(5)
    }
    MAX-ACCESS 	read-write
    STATUS 	current
    DESCRIPTION 	"Waveform display mode"

    ::= { wfmEntry 6 }


wfmChromaOffset OBJECT-TYPE
    SYNTAX 	INTEGER {
        off(0),
        on(1)
    }
    MAX-ACCESS 	read-write
    STATUS 	current
    DESCRIPTION 	"Waveform chroma offset enable"

    ::= { wfmEntry 7 }


wfmYCbCrChanEnable OBJECT-TYPE
    SYNTAX 	DisplayString
    MAX-ACCESS 	read-write
    STATUS 	current
    DESCRIPTION 	"Waveform components enabled in YCbCr(YPbPr) Color space. Possible values: Y, Cb(or Pb), Cr(or Pr), YCb(or YPb), YCr (or YPr), CbCr (or PbPr), YCbCr (or YPbPr). For dual link input, A (alpha trace) is also allowed along with Y, Cb(or Pb) and Cr(or Pr)."

    ::= { wfmEntry 8 }


wfmYRGBChanEnable OBJECT-TYPE
    SYNTAX 	DisplayString
    MAX-ACCESS 	read-write
    STATUS 	current
    DESCRIPTION 	"Waveform components enabled in YRGB Color space. Possible values: Y, R, G, B, YR, YG, YB, RG, RB, GB, YRG, YRB, YGB, RGB, YRGB"

    ::= { wfmEntry 9 }


wfmRGBChanEnable OBJECT-TYPE
    SYNTAX 	DisplayString
    MAX-ACCESS 	read-write
    STATUS 	current
    DESCRIPTION 	"Waveform components enabled in RGB Color space. Possible values: R, G, B, RG, GB, RB, RGB. For dual link input, A(alpha trace) is also allowed along with R, G and B."

    ::= { wfmEntry 10 }


wfmSweepMode    OBJECT-TYPE
    SYNTAX 	INTEGER {
        h1(1),
        h2(2),
        f1(3),
        f2(4)
    }
    MAX-ACCESS 	read-write
    STATUS 	current
    DESCRIPTION 	"Waveform sweep mode and timbase"

    ::= { wfmEntry 11 }


wfmGainMode     OBJECT-TYPE
    SYNTAX 	INTEGER {
        gain-x1(0),
        gain-x5(1),
        gain-x10(2),
        gain-x2(3)
    }
    MAX-ACCESS 	read-write
    STATUS 	current
    DESCRIPTION 	"Waveform fixed gain values"

    ::= { wfmEntry 12 }


wfmVarGainEnable OBJECT-TYPE
    SYNTAX 	INTEGER {
        off(0),
        on(1)
    }
    MAX-ACCESS 	read-write
    STATUS 	current
    DESCRIPTION 	"Enable/diable waveform variable gain"

    ::= { wfmEntry 13 }


wfmVarGain      OBJECT-TYPE
    SYNTAX 	DisplayString
    MAX-ACCESS 	read-write
    STATUS 	current
    DESCRIPTION 	"Waveform variable gain values (effective). Range of values depends on current value of wfmGainMode."

    ::= { wfmEntry 14 }


wfmCursorMode   OBJECT-TYPE
    SYNTAX 	INTEGER {
        volt(0),
        time(1),
        voltAndTime(2)
    }
    MAX-ACCESS 	read-write
    STATUS 	current
    DESCRIPTION 	"Select waveform cursor mode"

    ::= { wfmEntry 15 }


wfmCursorActive OBJECT-TYPE
    SYNTAX 	INTEGER {
        off(0),
        on(1)
    }
    MAX-ACCESS 	read-write
    STATUS 	current
    DESCRIPTION 	"Enable/Disable waveform cursors"

    ::= { wfmEntry 16 }


wfmCursorH1Pos  OBJECT-TYPE
    SYNTAX 	DisplayString
    MAX-ACCESS 	read-write
    STATUS 	current
    DESCRIPTION 	"Position of the first horizontal cursor in waveform display.The range of values depends on the current video input format and the sweep time base. Time values may be expressed as milliseconds (ms) or microseconds"

    ::= { wfmEntry 17 }


wfmCursorH2Pos  OBJECT-TYPE
    SYNTAX 	DisplayString
    MAX-ACCESS 	read-write
    STATUS 	current
    DESCRIPTION 	"Position of the second horizontal cursor in waveform display.The range of values depends on the current video input format and the sweep time base. Time values may be expressed as milliseconds (ms) or microseconds"

    ::= { wfmEntry 18 }


wfmCursorV1Pos  OBJECT-TYPE
    SYNTAX 	DisplayString
    MAX-ACCESS 	read-write
    STATUS 	current
    DESCRIPTION 	"Position of the first vertical cursor in waveform display in voltage relative to sweep position"

    ::= { wfmEntry 19 }


wfmCursorV2Pos  OBJECT-TYPE
    SYNTAX 	DisplayString
    MAX-ACCESS 	read-write
    STATUS 	current
    DESCRIPTION 	"Position of the second vertical cursor in waveform display in voltage relative to sweep position"

    ::= { wfmEntry 20 }


wfmCursorHDelta OBJECT-TYPE
    SYNTAX 	DisplayString
    MAX-ACCESS 	read-only
    STATUS 	current
    DESCRIPTION 	"Time difference between horizontal cursors"

    ::= { wfmEntry 21 }


wfmCursorVDelta OBJECT-TYPE
    SYNTAX 	DisplayString
    MAX-ACCESS 	read-only
    STATUS 	current
    DESCRIPTION 	"Time difference between vertical cursors"

    ::= { wfmEntry 22 }


wfmHorPos       OBJECT-TYPE
    SYNTAX 	DisplayString
    MAX-ACCESS 	read-write
    STATUS 	current
    DESCRIPTION 	"Waveform horizontal position as offset from center"

    ::= { wfmEntry 23 }


wfmVertPos      OBJECT-TYPE
    SYNTAX 	DisplayString
    MAX-ACCESS 	read-write
    STATUS 	current
    DESCRIPTION 	"Waveform vertical position in units of mV"

    ::= { wfmEntry 24 }


wfmHMag         OBJECT-TYPE
    SYNTAX 	INTEGER {
        off(0),
        on(1),
        gain-x10(10),
        gain-x20(20),
        gain-x25(25),
        gain-x50(50)
    }
    MAX-ACCESS 	read-write
    STATUS 	current
    DESCRIPTION 	"Enable/Disable waveform horizontal magnification"

    ::= { wfmEntry 25 }


wfmCenter       OBJECT-TYPE
    SYNTAX 	INTEGER {
        off(0),
        on(1)
    }
    MAX-ACCESS 	read-write
    STATUS 	current
    DESCRIPTION 	"Center waveform (write only)"

    ::= { wfmEntry 26 }


wfmPercentCurUnits OBJECT-TYPE
    SYNTAX 	INTEGER {
        mv(0),
        percent(1)
    }
    MAX-ACCESS 	read-write
    STATUS 	current
    DESCRIPTION 	"Units of measure for veritcal cursors"

    ::= { wfmEntry 27 }


wfmOneOverTCurUnits OBJECT-TYPE
    SYNTAX 	INTEGER {
        sec(0),
        oneOverT(1)
    }
    MAX-ACCESS 	read-write
    STATUS 	current
    DESCRIPTION 	"Units of measure for horizontal cursor delta as time or 1/t."

    ::= { wfmEntry 28 }


wfmSetCur100Percent OBJECT-TYPE
    SYNTAX 	INTEGER
    MAX-ACCESS 	read-write
    STATUS 	current
    DESCRIPTION 	"Sets current vertical cursor positions as 0% and 100% reference levels for normal waveform display (write-only)"

    ::= { wfmEntry 29 }


old-bowtiePercentCurUnits OBJECT-TYPE
    SYNTAX 	INTEGER {
        mv(0),
        percent(1)
    }
    MAX-ACCESS 	read-write
    STATUS 	deprecated
    DESCRIPTION 	"Units of measure for vertical cursors in Bowtie display"

    ::= { wfmEntry 30 }


old-bowtieOneOverTCurUnits OBJECT-TYPE
    SYNTAX 	INTEGER {
        sec(0),
        oneOverT(1)
    }
    MAX-ACCESS 	read-write
    STATUS 	deprecated
    DESCRIPTION 	"Units of measure for time cursors in Bowtie display as time to 1/t"

    ::= { wfmEntry 31 }


old-bowtieSetCur100Percent OBJECT-TYPE
    SYNTAX 	INTEGER
    MAX-ACCESS 	read-write
    STATUS 	deprecated
    DESCRIPTION 	"Sets current vertical cursor position as 0% and 100% reference levels for Bowtie display (write-only)"

    ::= { wfmEntry 32 }


wfmCpstChanEnable OBJECT-TYPE
    SYNTAX 	DisplayString
    MAX-ACCESS 	read-write
    STATUS 	current
    DESCRIPTION 	"Waveform components enabled in Composite color space Possible values: Flat, Luma, Chroma, Flat Luma, Luma Chroma, Flat Chroma, Flat Luma Chroma"

    ::= { wfmEntry 33 }


wfmFixedHMag    OBJECT-TYPE
    SYNTAX 	INTEGER {
        gain-x1(0),
        gain-x10(1),
        gain-x20(2),
        gain-x50(3)
    }
    MAX-ACCESS 	read-write
    STATUS 	deprecated
    DESCRIPTION 	"Waveform horizontal fixed magnification value"

    ::= { wfmEntry 34 }


old-bowtieHMag  OBJECT-TYPE
    SYNTAX 	INTEGER {
        off(0),
        on(1),
        gain-x10(10),
        gain-x20(20),
        gain-x25(25),
        gain-x50(50)
    }
    MAX-ACCESS 	read-write
    STATUS 	deprecated
    DESCRIPTION 	"Enable/Disable bowtie horizontal magnification"

    ::= { wfmEntry 35 }


old-bowtieFixedHMag OBJECT-TYPE
    SYNTAX 	INTEGER {
        gain-x1(0),
        gain-x10(1),
        gain-x20(2),
        gain-x25(3),
        gain-x50(4)
    }
    MAX-ACCESS 	read-write
    STATUS 	deprecated
    DESCRIPTION 	"Bowtie horizontal fixed magnification value"

    ::= { wfmEntry 36 }


wfmXYZChanEnable OBJECT-TYPE
    SYNTAX 	DisplayString
    MAX-ACCESS 	read-write
    STATUS 	current
    DESCRIPTION 	"Waveform channels enabled in XYZ mode. Possible values: X, Y, Z, A (alhpa channel) or combination of these."

    ::= { wfmEntry 37 }


wfmFilterXyz    OBJECT-TYPE
    SYNTAX 	INTEGER {
        flat(0),
        lowpass(1)
    }
    MAX-ACCESS 	read-write
    STATUS 	current
    DESCRIPTION 	"Waveform filter for XYZ display mode."

    ::= { wfmEntry 38 }


wfmMultiChannel OBJECT-TYPE
    SYNTAX 	INTEGER {
        y(0),
        cb(1),
        cr(2),
        r(3),
        g(4),
        b(5),
        cieX(6),
        cieY(7),
        cieZ(8),
        composite(9),
        luma(10),
        chroma(11)
    }
    MAX-ACCESS 	read-write
    STATUS 	current
    DESCRIPTION 	"Selects the component channel to display for all inputs in camera balance mode. Only one channel shall be selected."

    ::= { wfmEntry 39 }


wfmFilterMulti  OBJECT-TYPE
    SYNTAX 	INTEGER {
        flat(0),
        lowpass(1)
    }
    MAX-ACCESS 	read-write
    STATUS 	current
    DESCRIPTION 	"Waveform filter for Multi Input display mode."

    ::= { wfmEntry 40 }


wfmTimePerDiv   OBJECT-TYPE
    SYNTAX 	DisplayString
    MAX-ACCESS 	read-only
    STATUS 	current
    DESCRIPTION 	"The time per division of the waveform trace."

    ::= { wfmEntry 41 }


wfmTable        OBJECT-TYPE
    SYNTAX 	SEQUENCE OF WfmEntry
    MAX-ACCESS 	not-accessible
    STATUS 	current
    DESCRIPTION 	"Table for wfm mode"

    ::= { wfm 1 }


wfmEntry        OBJECT-TYPE
    SYNTAX 	WfmEntry
    MAX-ACCESS 	not-accessible
    STATUS 	current
    DESCRIPTION 	"A row in the WFM Table"
    INDEX { currTile }

    ::= { wfmTable 1 }


WfmEntry ::= SEQUENCE {
    wfmMode 	INTEGER,
    wfmFilterCpst 	INTEGER,
    wfmFilterYcbcr 	INTEGER,
    wfmFilterRgb 	INTEGER,
    wfmFilterYrgb 	INTEGER,
    wfmColorSpace 	INTEGER,
    wfmChromaOffset 	INTEGER,
    wfmYCbCrChanEnable 	DisplayString,
    wfmYRGBChanEnable 	DisplayString,
    wfmRGBChanEnable 	DisplayString,
    wfmSweepMode 	INTEGER,
    wfmGainMode 	INTEGER,
    wfmVarGainEnable 	INTEGER,
    wfmVarGain 	DisplayString,
    wfmCursorMode 	INTEGER,
    wfmCursorActive 	INTEGER,
    wfmCursorH1Pos 	DisplayString,
    wfmCursorH2Pos 	DisplayString,
    wfmCursorV1Pos 	DisplayString,
    wfmCursorV2Pos 	DisplayString,
    wfmCursorHDelta 	DisplayString,
    wfmCursorVDelta 	DisplayString,
    wfmHorPos 	DisplayString,
    wfmVertPos 	DisplayString,
    wfmHMag 	INTEGER,
    wfmCenter 	INTEGER,
    wfmPercentCurUnits 	INTEGER,
    wfmOneOverTCurUnits 	INTEGER,
    wfmSetCur100Percent 	INTEGER,
    old-bowtiePercentCurUnits 	INTEGER,
    old-bowtieOneOverTCurUnits 	INTEGER,
    old-bowtieSetCur100Percent 	INTEGER,
    wfmCpstChanEnable 	DisplayString,
    wfmFixedHMag 	INTEGER,
    old-bowtieHMag 	INTEGER,
    old-bowtieFixedHMag 	INTEGER,
    wfmXYZChanEnable 	DisplayString,
    wfmFilterXyz 	INTEGER,
    wfmMultiChannel 	INTEGER,
    wfmFilterMulti 	INTEGER,
    wfmTimePerDiv 	DisplayString 
}
-- 
-- vec Group
-- Vector display mode variables

vecPhase        OBJECT-TYPE
    SYNTAX 	DisplayString
    MAX-ACCESS 	read-write
    STATUS 	current
    DESCRIPTION 	"Vector phase for composite input only (0.0 to 360.0 degrees)."

    ::= { vec 1 }


vecMode         OBJECT-TYPE
    SYNTAX 	INTEGER {
        normal(0),
        sdi-composite(1),
        sch-phase(2)
    }
    MAX-ACCESS 	read-write
    STATUS 	current
    DESCRIPTION 	"Vector display mode."

    ::= { vecEntry 1 }


vecHorPos       OBJECT-TYPE
    SYNTAX 	DisplayString
    MAX-ACCESS 	read-write
    STATUS 	current
    DESCRIPTION 	"Vector horizontal position in units of mV"

    ::= { vecEntry 2 }


vecVertPos      OBJECT-TYPE
    SYNTAX 	DisplayString
    MAX-ACCESS 	read-write
    STATUS 	current
    DESCRIPTION 	"Vector vertical position in units of mV"

    ::= { vecEntry 3 }


vecTargets      OBJECT-TYPE
    SYNTAX 	INTEGER {
        bar-75-percent(0),
        bar-100-percent(1)
    }
    MAX-ACCESS 	read-write
    STATUS 	current
    DESCRIPTION 	"Vector bar targets (75% or 100%)."

    ::= { vecEntry 4 }


vecGain         OBJECT-TYPE
    SYNTAX 	INTEGER {
        gain-x1(0),
        gain-x5(1),
        gain-x10(2),
        gain-x2(3)
    }
    MAX-ACCESS 	read-write
    STATUS 	current
    DESCRIPTION 	"Vector fixed gain."

    ::= { vecEntry 5 }


vecVarGainEnable OBJECT-TYPE
    SYNTAX 	INTEGER {
        off(0),
        on(1)
    }
    MAX-ACCESS 	read-write
    STATUS 	current
    DESCRIPTION 	"Enable/disable vector variable gain."

    ::= { vecEntry 6 }


vecVarGain      OBJECT-TYPE
    SYNTAX 	DisplayString
    MAX-ACCESS 	read-write
    STATUS 	current
    DESCRIPTION 	"Vector variable gain (effective). Range of values depend on current value of vecGain."

    ::= { vecEntry 7 }


vecCenter       OBJECT-TYPE
    SYNTAX 	INTEGER {
        on-black(0),
        on-red(1),
        on-magenta(2),
        on-yellow(3),
        on-blue(4),
        on-green(5),
        on-cyan(6)
    }
    MAX-ACCESS 	read-write
    STATUS 	current
    DESCRIPTION 	"Center vector on display. On some instruments, the selected color bar target may be positioned at the center of the display (write-only)."

    ::= { vecEntry 8 }


vecLqvEnable    OBJECT-TYPE
    SYNTAX 	INTEGER {
        off(0),
        on(1)
    }
    MAX-ACCESS 	read-write
    STATUS 	current
    DESCRIPTION 	"Enable/disable Luma Qualified Vector(LQV)."

    ::= { vecEntry 9 }


vecLumaLow      OBJECT-TYPE
    SYNTAX 	INTEGER (0..1023)
    MAX-ACCESS 	read-write
    STATUS 	current
    DESCRIPTION 	"Lower luma limit for Luma Qualified Vector."

    ::= { vecEntry 10 }


vecLumaHigh     OBJECT-TYPE
    SYNTAX 	INTEGER (0..1023)
    MAX-ACCESS 	read-write
    STATUS 	current
    DESCRIPTION 	"Higher luma limit for Luma Qualified Vector."

    ::= { vecEntry 11 }


vecTable        OBJECT-TYPE
    SYNTAX 	SEQUENCE OF VecEntry
    MAX-ACCESS 	not-accessible
    STATUS 	current
    DESCRIPTION 	"Table for vector display mode"

    ::= { vec 2 }


vecEntry        OBJECT-TYPE
    SYNTAX 	VecEntry
    MAX-ACCESS 	not-accessible
    STATUS 	current
    DESCRIPTION 	"a row in the vector table"
    INDEX { currTile }

    ::= { vecTable 1 }


VecEntry ::= SEQUENCE {
    vecMode 	INTEGER,
    vecHorPos 	DisplayString,
    vecVertPos 	DisplayString,
    vecTargets 	INTEGER,
    vecGain 	INTEGER,
    vecVarGainEnable 	INTEGER,
    vecVarGain 	DisplayString,
    vecCenter 	INTEGER,
    vecLqvEnable 	INTEGER,
    vecLumaLow 	INTEGER,
    vecLumaHigh 	INTEGER 
}
-- 
-- arr Group
-- Arrowhead display mode variables

arrMode         OBJECT-TYPE
    SYNTAX 	INTEGER {
        normal(0),
        setup(1)
    }
    MAX-ACCESS 	read-write
    STATUS 	current
    DESCRIPTION 	"Arrowhead display mode."

    ::= { arrEntry 1 }


arrFmt          OBJECT-TYPE
    SYNTAX 	INTEGER {
        ntsc(0),
        pal(1),
        auto(2)
    }
    MAX-ACCESS 	read-write
    STATUS 	current
    DESCRIPTION 	"Arrowhead destination video format. Selected format determines gamut limits and graticule."

    ::= { arrEntry 2 }


arrTable        OBJECT-TYPE
    SYNTAX 	SEQUENCE OF ArrEntry
    MAX-ACCESS 	not-accessible
    STATUS 	current
    DESCRIPTION 	"Table for arrowhead display mode"

    ::= { arr 1 }


arrEntry        OBJECT-TYPE
    SYNTAX 	ArrEntry
    MAX-ACCESS 	not-accessible
    STATUS 	current
    DESCRIPTION 	"a row in the arrowhead table"
    INDEX { currTile }

    ::= { arrTable 1 }


ArrEntry ::= SEQUENCE {
    arrMode 	INTEGER,
    arrFmt 	INTEGER 
}
-- 
-- lgt Group
-- Lightning display mode variables

lgtHorPos       OBJECT-TYPE
    SYNTAX 	DisplayString
    MAX-ACCESS 	read-write
    STATUS 	current
    DESCRIPTION 	"Lightning horizontal position in mV"

    ::= { lgtEntry 1 }


lgtVertPos      OBJECT-TYPE
    SYNTAX 	DisplayString
    MAX-ACCESS 	read-write
    STATUS 	current
    DESCRIPTION 	"Lightning vertical position in mV"

    ::= { lgtEntry 2 }


lgtHorGain      OBJECT-TYPE
    SYNTAX 	INTEGER {
        gain-x1(0),
        gain-x5(1),
        gain-x10(2),
        gain-x2(3)
    }
    MAX-ACCESS 	read-write
    STATUS 	current
    DESCRIPTION 	"Lightning horizontal(chroma) fixed gain."

    ::= { lgtEntry 3 }


lgtVertGain     OBJECT-TYPE
    SYNTAX 	INTEGER {
        gain-x1(0),
        gain-x5(1),
        gain-x10(2),
        gain-x2(3)
    }
    MAX-ACCESS 	read-write
    STATUS 	current
    DESCRIPTION 	"Lightning vertical(luma) fixed gain."

    ::= { lgtEntry 4 }


lgtVarHGainEnable OBJECT-TYPE
    SYNTAX 	INTEGER {
        off(0),
        on(1)
    }
    MAX-ACCESS 	read-write
    STATUS 	current
    DESCRIPTION 	"Enable/disable lightning horizontal(chroma) variable gain."

    ::= { lgtEntry 5 }


lgtVarHorGain   OBJECT-TYPE
    SYNTAX 	DisplayString
    MAX-ACCESS 	read-write
    STATUS 	current
    DESCRIPTION 	"Lightning effective variable horizontal(chroma) gain. Range of values depend on current value of lgtHorGain."

    ::= { lgtEntry 6 }


lgtVarVGainEnable OBJECT-TYPE
    SYNTAX 	INTEGER {
        off(0),
        on(1)
    }
    MAX-ACCESS 	read-write
    STATUS 	current
    DESCRIPTION 	"Enable/disable lightning vertical(luma) variable gain."

    ::= { lgtEntry 7 }


lgtVarVertGain  OBJECT-TYPE
    SYNTAX 	DisplayString
    MAX-ACCESS 	read-write
    STATUS 	current
    DESCRIPTION 	"Lightning effective variable vertical(luma) gain. Range of values depend on current value of lgtVertGain."

    ::= { lgtEntry 8 }


lgtCenter       OBJECT-TYPE
    SYNTAX 	INTEGER {
        off(0),
        on(1)
    }
    MAX-ACCESS 	read-write
    STATUS 	current
    DESCRIPTION 	"Center waveform in lightning mode."

    ::= { lgtEntry 9 }


lgtTargets      OBJECT-TYPE
    SYNTAX 	INTEGER {
        bar-75-percent(0),
        bar-100-percent(1)
    }
    MAX-ACCESS 	read-write
    STATUS 	current
    DESCRIPTION 	"Lightning bar targets(75% or 100%)."

    ::= { lgtEntry 10 }


lgtTable        OBJECT-TYPE
    SYNTAX 	SEQUENCE OF LgtEntry
    MAX-ACCESS 	not-accessible
    STATUS 	current
    DESCRIPTION 	"Table for lightning display mode"

    ::= { lgt 1 }


lgtEntry        OBJECT-TYPE
    SYNTAX 	LgtEntry
    MAX-ACCESS 	not-accessible
    STATUS 	current
    DESCRIPTION 	"a row in the lightning table"
    INDEX { currTile }

    ::= { lgtTable 1 }


LgtEntry ::= SEQUENCE {
    lgtHorPos 	DisplayString,
    lgtVertPos 	DisplayString,
    lgtHorGain 	INTEGER,
    lgtVertGain 	INTEGER,
    lgtVarHGainEnable 	INTEGER,
    lgtVarHorGain 	DisplayString,
    lgtVarVGainEnable 	INTEGER,
    lgtVarVertGain 	DisplayString,
    lgtCenter 	INTEGER,
    lgtTargets 	INTEGER 
}
-- 
-- dmd Group
-- Diamond display mode variables
--  ::= { dmd 1 }
--  ::= { dmd 2 }
--  ::= { dmd 3 }

dmdMode         OBJECT-TYPE
    SYNTAX 	INTEGER {
        diamond(0),
        split-diamond(1)
    }
    MAX-ACCESS 	read-write
    STATUS 	current
    DESCRIPTION 	"Diamond display mode."

    ::= { dmdEntry 1 }


dmdTable        OBJECT-TYPE
    SYNTAX 	SEQUENCE OF DmdEntry
    MAX-ACCESS 	not-accessible
    STATUS 	current
    DESCRIPTION 	"Table for diamond display mode"

    ::= { dmd 4 }


dmdEntry        OBJECT-TYPE
    SYNTAX 	DmdEntry
    MAX-ACCESS 	not-accessible
    STATUS 	current
    DESCRIPTION 	"a row in the diamond table"
    INDEX { currTile }

    ::= { dmdTable 1 }


DmdEntry ::= SEQUENCE {
    dmdMode 	INTEGER 
}
-- 
-- pict Group
-- Picture display mode variables

pictFrame       OBJECT-TYPE
    SYNTAX 	INTEGER {
        off(0),
        on(1)
    }
    MAX-ACCESS 	read-write
    STATUS 	current
    DESCRIPTION 	"Enable/disable picture frame."

    ::= { pictEntry 1 }


pictCursorLine  OBJECT-TYPE
    SYNTAX 	INTEGER {
        off(0),
        on(1)
    }
    MAX-ACCESS 	read-write
    STATUS 	current
    DESCRIPTION 	"Enable/disable line select cursor in picture."

    ::= { pictEntry 2 }


safeAreaAction1 OBJECT-TYPE
    SYNTAX 	INTEGER {
        off(0),
        auto(1),
        aspect4X3(2),
        aspect14X9(3),
        aspect16X9(4),
        custom-1(5),
        custom-2(6),
        aspect1-85(7),
        aspect2-20(8),
        aspect2-35(9)
    }
    MAX-ACCESS 	read-write
    STATUS 	current
    DESCRIPTION 	"Select first safe action graticule type."

    ::= { pictEntry 3 }


safeAreaTitle1  OBJECT-TYPE
    SYNTAX 	INTEGER {
        off(0),
        auto(1),
        aspect4X3(2),
        aspect14X9(3),
        aspect16X9(4),
        custom-1(5),
        custom-2(6),
        aspect1-85(7),
        aspect2-20(8),
        aspect2-35(9)
    }
    MAX-ACCESS 	read-write
    STATUS 	current
    DESCRIPTION 	"Select first safe title graticule type."

    ::= { pictEntry 4 }


safeAreaAction2 OBJECT-TYPE
    SYNTAX 	INTEGER {
        off(0),
        auto(1),
        aspect4X3(2),
        aspect14X9(3),
        aspect16X9(4),
        custom-1(5),
        custom-2(6),
        aspect1-85(7),
        aspect2-20(8),
        aspect2-35(9)
    }
    MAX-ACCESS 	read-write
    STATUS 	current
    DESCRIPTION 	"Select second safe action graticule type."

    ::= { pictEntry 5 }


safeAreaTitle2  OBJECT-TYPE
    SYNTAX 	INTEGER {
        off(0),
        auto(1),
        aspect4X3(2),
        aspect14X9(3),
        aspect16X9(4),
        custom-1(5),
        custom-2(6),
        aspect1-85(7),
        aspect2-20(8),
        aspect2-35(9)
    }
    MAX-ACCESS 	read-write
    STATUS 	current
    DESCRIPTION 	"Select second safe title graticule type."

    ::= { pictEntry 6 }


pictCenterGrat  OBJECT-TYPE
    SYNTAX 	INTEGER {
        off(0),
        on(1)
    }
    MAX-ACCESS 	read-write
    STATUS 	current
    DESCRIPTION 	"Enable/disable display of picture center graticule."

    ::= { pictEntry 7 }


ccDisplayFormat OBJECT-TYPE
    SYNTAX 	INTEGER {
        off(0),
        auto(1),
        cea608(2),
        cea708(3),
        wst(4)
    }
    MAX-ACCESS 	read-write
    STATUS 	current
    DESCRIPTION 	"Enable/disable the closed captions or teletext display in the selected tile and select the format."

    ::= { pictEntry 8 }


ccService608Tile OBJECT-TYPE
    SYNTAX 	INTEGER {
        cc1(1),
        cc2(2),
        cc3(3),
        cc4(4),
        text1(5),
        text2(6),
        text3(7),
        text4(8)
    }
    MAX-ACCESS 	read-write
    STATUS 	current
    DESCRIPTION 	"Closed caption service 608 channel selection in the selected tile."

    ::= { pictEntry 9 }


pictLinkSelect  OBJECT-TYPE
    SYNTAX 	INTEGER {
        links-combined(0),
        link-a(1),
        link-b(2),
        alpha(3)
    }
    MAX-ACCESS 	read-write
    STATUS 	current
    DESCRIPTION 	"Link selection in picture display for dual link signal."

    ::= { pictEntry 10 }


ccService708Tile OBJECT-TYPE
    SYNTAX 	INTEGER {
        service1(1),
        service2(2),
        service3(3),
        service4(4),
        service5(5),
        service6(6)
    }
    MAX-ACCESS 	read-write
    STATUS 	current
    DESCRIPTION 	"Closed caption service 708 channel selection in the selected tile."

    ::= { pictEntry 11 }


teletextPage    OBJECT-TYPE
    SYNTAX 	INTEGER (256..2303)
    MAX-ACCESS 	read-write
    STATUS 	current
    DESCRIPTION 	"Select the teletext page."

    ::= { pictEntry 12 }


pictAFDGrat     OBJECT-TYPE
    SYNTAX 	INTEGER {
        off(0),
        on(1)
    }
    MAX-ACCESS 	read-write
    STATUS 	current
    DESCRIPTION 	"Display control of AFD graticule."

    ::= { pictEntry 13 }


pictQualGrat    OBJECT-TYPE
    SYNTAX 	INTEGER {
        off(0),
        black(1),
        frozen(2)
    }
    MAX-ACCESS 	read-write
    STATUS 	current
    DESCRIPTION 	"Display picture quality graticules for black or frozen."

    ::= { pictEntry 14 }


pict3dDisplay   OBJECT-TYPE
    SYNTAX 	INTEGER {
        raw(0),
        overlay(1),
        left(2),
        right(3),
        leftMinusRight(4),
        rightMinusLeft(5),
        anaglyphRedCy(6),
        anaglyphGreenMg(7),
        checkerBoard(8)
    }
    MAX-ACCESS 	read-write
    STATUS 	current
    DESCRIPTION 	"3D picture display mode.  Raw is only valid for frame-compatible 3D formats and will display as overlay for all other 3D formats."

    ::= { pictEntry 15 }


pictDisparityMeas OBJECT-TYPE
    SYNTAX 	INTEGER {
        off(0),
        grid(1),
        cursorMeas(2)
    }
    MAX-ACCESS 	read-write
    STATUS 	current
    DESCRIPTION 	"For disparity measure, choose off, disparity grid, or disparity measure using cursors"

    ::= { pictEntry 16 }


dispGridHPercent OBJECT-TYPE
    SYNTAX 	INTEGER (1..15)
    MAX-ACCESS 	read-write
    STATUS 	current
    DESCRIPTION 	"Horizontal percent of disparity grid with respect to picture"

    ::= { pictEntry 18 }


dispGridVOffset OBJECT-TYPE
    SYNTAX 	DisplayString
    MAX-ACCESS 	read-write
    STATUS 	current
    DESCRIPTION 	"Vertical offset control of the disparity grid. The units are percent in relation to active lines of picture."

    ::= { pictEntry 19 }


dispGridHOffset OBJECT-TYPE
    SYNTAX 	DisplayString
    MAX-ACCESS 	read-write
    STATUS 	current
    DESCRIPTION 	"Horizontal offset control of the disparity grid. The units are percent in relation to active samples of picture."

    ::= { pictEntry 20 }


pictTable       OBJECT-TYPE
    SYNTAX 	SEQUENCE OF PictEntry
    MAX-ACCESS 	not-accessible
    STATUS 	current
    DESCRIPTION 	"Table for picture display mode"

    ::= { pict 1 }


pictEntry       OBJECT-TYPE
    SYNTAX 	PictEntry
    MAX-ACCESS 	not-accessible
    STATUS 	current
    DESCRIPTION 	"a row in the picture table"
    INDEX { currTile }

    ::= { pictTable 1 }


PictEntry ::= SEQUENCE {
    pictFrame 	INTEGER,
    pictCursorLine 	INTEGER,
    safeAreaAction1 	INTEGER,
    safeAreaTitle1 	INTEGER,
    safeAreaAction2 	INTEGER,
    safeAreaTitle2 	INTEGER,
    pictCenterGrat 	INTEGER,
    ccDisplayFormat 	INTEGER,
    ccService608Tile 	INTEGER,
    pictLinkSelect 	INTEGER,
    ccService708Tile 	INTEGER,
    teletextPage 	INTEGER,
    pictAFDGrat 	INTEGER,
    pictQualGrat 	INTEGER,
    pict3dDisplay 	INTEGER,
    pictDisparityMeas 	INTEGER,
    dispGridHPercent 	INTEGER,
    dispGridVOffset 	DisplayString,
    dispGridHOffset 	DisplayString 
}

safeAreaStandard OBJECT-TYPE
    SYNTAX 	INTEGER {
        smpte(0),
        itu(1),
        arib-b4(2),
        smpte-2046(3)
    }
    MAX-ACCESS 	read-write
    STATUS 	current
    DESCRIPTION 	"Standard used for safe area graticule."

    ::= { pict 2 }


cstmSafeAction1Width OBJECT-TYPE
    SYNTAX 	INTEGER (0..10000)
    MAX-ACCESS 	read-write
    STATUS 	current
    DESCRIPTION 	"Width of safe area region to target aperture, expressed in units of 0.01%."

    ::= { pict 3 }


cstmSafeAction1Height OBJECT-TYPE
    SYNTAX 	INTEGER (0..10000)
    MAX-ACCESS 	read-write
    STATUS 	current
    DESCRIPTION 	"Height of safe area region to target aperture, expressed in units of 0.01%."

    ::= { pict 4 }


cstmSafeAction1HOffset OBJECT-TYPE
    SYNTAX 	INTEGER (-5000..5000)
    MAX-ACCESS 	read-write
    STATUS 	current
    DESCRIPTION 	"Horizontal offset of safe area region from center of target aperture, expressed in units of 0.01%."

    ::= { pict 5 }


cstmSafeAction1VOffset OBJECT-TYPE
    SYNTAX 	INTEGER (-5000..5000)
    MAX-ACCESS 	read-write
    STATUS 	current
    DESCRIPTION 	"Vertical offset of safe area region from center of target aperture, expressed in units of 0.01%."

    ::= { pict 6 }


cstmSafeTitle1Width OBJECT-TYPE
    SYNTAX 	INTEGER (0..10000)
    MAX-ACCESS 	read-write
    STATUS 	current
    DESCRIPTION 	"Width of safe title region to target aperture, expressed in units of 0.01%."

    ::= { pict 7 }


cstmSafeTitle1Height OBJECT-TYPE
    SYNTAX 	INTEGER (0..10000)
    MAX-ACCESS 	read-write
    STATUS 	current
    DESCRIPTION 	"Height of safe title region to target aperture, expressed in units of 0.01%."

    ::= { pict 8 }


cstmSafeTitle1HOffset OBJECT-TYPE
    SYNTAX 	INTEGER (-5000..5000)
    MAX-ACCESS 	read-write
    STATUS 	current
    DESCRIPTION 	"Horizontal offset of safe title region from center of target aperture, expressed in units of 0.01%."

    ::= { pict 9 }


cstmSafeTitle1VOffset OBJECT-TYPE
    SYNTAX 	INTEGER (-5000..5000)
    MAX-ACCESS 	read-write
    STATUS 	current
    DESCRIPTION 	"Vertical offset of safe title region from center of target aperture, expressed in units of 0.01%."

    ::= { pict 10 }


cstmSafeAction2Width OBJECT-TYPE
    SYNTAX 	INTEGER (0..10000)
    MAX-ACCESS 	read-write
    STATUS 	current
    DESCRIPTION 	"Width of safe area region to target aperture, expressed in units of 0.01%."

    ::= { pict 11 }


cstmSafeAction2Height OBJECT-TYPE
    SYNTAX 	INTEGER (0..10000)
    MAX-ACCESS 	read-write
    STATUS 	current
    DESCRIPTION 	"Height of safe area region to target aperture, expressed in units of 0.01%."

    ::= { pict 12 }


cstmSafeAction2HOffset OBJECT-TYPE
    SYNTAX 	INTEGER (-5000..5000)
    MAX-ACCESS 	read-write
    STATUS 	current
    DESCRIPTION 	"Horizontal offset of safe area region from center of target aperture, expressed in units of 0.01%."

    ::= { pict 13 }


cstmSafeAction2VOffset OBJECT-TYPE
    SYNTAX 	INTEGER (-5000..5000)
    MAX-ACCESS 	read-write
    STATUS 	current
    DESCRIPTION 	"Vertical offset of safe area region from center of target aperture, expressed in units of 0.01%."

    ::= { pict 14 }


cstmSafeTitle2Width OBJECT-TYPE
    SYNTAX 	INTEGER (0..10000)
    MAX-ACCESS 	read-write
    STATUS 	current
    DESCRIPTION 	"Width of safe title region to target aperture, expressed in units of 0.01%."

    ::= { pict 15 }


cstmSafeTitle2Height OBJECT-TYPE
    SYNTAX 	INTEGER (0..10000)
    MAX-ACCESS 	read-write
    STATUS 	current
    DESCRIPTION 	"Height of safe title region to target aperture, expressed in units of 0.01%."

    ::= { pict 16 }


cstmSafeTitle2HOffset OBJECT-TYPE
    SYNTAX 	INTEGER (-5000..5000)
    MAX-ACCESS 	read-write
    STATUS 	current
    DESCRIPTION 	"Horizontal offset of safe title region from center of target aperture, expressed in units of 0.01%."

    ::= { pict 17 }


cstmSafeTitle2VOffset OBJECT-TYPE
    SYNTAX 	INTEGER (-5000..5000)
    MAX-ACCESS 	read-write
    STATUS 	current
    DESCRIPTION 	"Vertical offset of safe title region from center of target aperture, expressed in units of 0.01%."

    ::= { pict 18 }


dispGridColor   OBJECT-TYPE
    SYNTAX 	INTEGER {
        black(0),
        white(1),
        green(2)
    }
    MAX-ACCESS 	read-write
    STATUS 	current
    DESCRIPTION 	"Disparity Grid Color."

    ::= { pict 19 }


dispGridVertPercent OBJECT-TYPE
    SYNTAX 	INTEGER {
        ten(10),
        twentyFive(25),
        fifty(50)
    }
    MAX-ACCESS 	read-write
    STATUS 	current
    DESCRIPTION 	"Disparity grid's horizontal line spacing as percent of picture height."

    ::= { pict 20 }

-- 
-- sdistat group
-- SDI EDH status variables

sdiF1Crc        OBJECT-TYPE
    SYNTAX 	INTEGER
    MAX-ACCESS 	read-only
    STATUS 	current
    DESCRIPTION 	"SDI field 1 active picture CRC value. Use this OID for SD Only"

    ::= { sdistat 1 }


sdiF2Crc        OBJECT-TYPE
    SYNTAX 	INTEGER
    MAX-ACCESS 	read-only
    STATUS 	current
    DESCRIPTION 	"SDI field 2 active picture CRC value. Use this OID for SD Only"

    ::= { sdistat 2 }


sdiFfEdhErrSecs OBJECT-TYPE
    SYNTAX 	INTEGER
    MAX-ACCESS 	read-only
    STATUS 	current
    DESCRIPTION 	"Number of seconds with EDH error in full field."

    ::= { sdistat 3 }


sdiApEdhErrSecs OBJECT-TYPE
    SYNTAX 	INTEGER
    MAX-ACCESS 	read-only
    STATUS 	current
    DESCRIPTION 	"Number of seconds with EDH error in active picture."

    ::= { sdistat 4 }


sdiEdhReset     OBJECT-TYPE
    SYNTAX 	INTEGER {
        edh-reset(0),
        edh-stop(1),
        edh-run(2)
    }
    MAX-ACCESS 	read-write
    STATUS 	current
    DESCRIPTION 	"Resets, stops and runs the video session. To use in SIM mode, select channel with selectTile command"

    ::= { sdistat 5 }


sdiEdhFfErrField OBJECT-TYPE
    SYNTAX 	INTEGER
    MAX-ACCESS 	read-only
    STATUS 	current
    DESCRIPTION 	"Number of fields with full field EDH errors since last reset."

    ::= { sdistat 6 }


sdiEdhApErrField OBJECT-TYPE
    SYNTAX 	INTEGER
    MAX-ACCESS 	read-only
    STATUS 	current
    DESCRIPTION 	"Number of fields with active picture EDH errors since last reset."

    ::= { sdistat 7 }


sdiEdhFfPctErrField OBJECT-TYPE
    SYNTAX 	DisplayString
    MAX-ACCESS 	read-only
    STATUS 	current
    DESCRIPTION 	"% of fields with full field EDH errors since last reset."

    ::= { sdistat 8 }


sdiEdhApPctErrField OBJECT-TYPE
    SYNTAX 	DisplayString
    MAX-ACCESS 	read-only
    STATUS 	current
    DESCRIPTION 	"% of fields with active picture EDH errors since last reset."

    ::= { sdistat 9 }


sdiRgbErrSecs   OBJECT-TYPE
    SYNTAX 	INTEGER
    MAX-ACCESS 	read-only
    STATUS 	current
    DESCRIPTION 	"RGB errored seconds."

    ::= { sdistat 10 }


sdiRgbErrField  OBJECT-TYPE
    SYNTAX 	INTEGER
    MAX-ACCESS 	read-only
    STATUS 	current
    DESCRIPTION 	"RGB errored fields."

    ::= { sdistat 11 }


sdiRgbPctErrField OBJECT-TYPE
    SYNTAX 	DisplayString
    MAX-ACCESS 	read-only
    STATUS 	current
    DESCRIPTION 	"RGB % errored fields."

    ::= { sdistat 12 }


sdiCpstErrSecs  OBJECT-TYPE
    SYNTAX 	INTEGER
    MAX-ACCESS 	read-only
    STATUS 	current
    DESCRIPTION 	"Y+C errored seconds."

    ::= { sdistat 13 }


sdiCpstErrField OBJECT-TYPE
    SYNTAX 	INTEGER
    MAX-ACCESS 	read-only
    STATUS 	current
    DESCRIPTION 	"Y+C errored fields."

    ::= { sdistat 14 }


sdiCpstPctErrField OBJECT-TYPE
    SYNTAX 	DisplayString
    MAX-ACCESS 	read-only
    STATUS 	current
    DESCRIPTION 	"Y+C % errored fields."

    ::= { sdistat 15 }


sdiLumaErrSecs  OBJECT-TYPE
    SYNTAX 	INTEGER
    MAX-ACCESS 	read-only
    STATUS 	current
    DESCRIPTION 	"Luma errored seconds."

    ::= { sdistat 16 }


sdiLumaErrField OBJECT-TYPE
    SYNTAX 	INTEGER
    MAX-ACCESS 	read-only
    STATUS 	current
    DESCRIPTION 	"Luma errored fields."

    ::= { sdistat 17 }


sdiLumaPctErrField OBJECT-TYPE
    SYNTAX 	DisplayString
    MAX-ACCESS 	read-only
    STATUS 	current
    DESCRIPTION 	"Luma % errored fields."

    ::= { sdistat 18 }


sdiEdhErrSecs   OBJECT-TYPE
    SYNTAX 	INTEGER
    MAX-ACCESS 	read-only
    STATUS 	current
    DESCRIPTION 	" EDH Luma errored seconds."

    ::= { sdistat 19 }


sdiEdhErrField  OBJECT-TYPE
    SYNTAX 	INTEGER
    MAX-ACCESS 	read-only
    STATUS 	current
    DESCRIPTION 	"EDH Luma errored fields."

    ::= { sdistat 20 }


sdiEdhPctErrField OBJECT-TYPE
    SYNTAX 	DisplayString
    MAX-ACCESS 	read-only
    STATUS 	current
    DESCRIPTION 	"EDH Luma % errored fields."

    ::= { sdistat 21 }


sdi352Payload   OBJECT-TYPE
    SYNTAX 	DisplayString
    MAX-ACCESS 	read-only
    STATUS 	current
    DESCRIPTION 	"SDI 352 payload value."

    ::= { sdistat 22 }


sdiStuckbits    OBJECT-TYPE
    SYNTAX 	DisplayString
    MAX-ACCESS 	read-only
    STATUS 	current
    DESCRIPTION 	"Stuck bits in SD SDI data."

    ::= { sdistat 23 }


sdiYStuckbits   OBJECT-TYPE
    SYNTAX 	DisplayString
    MAX-ACCESS 	read-only
    STATUS 	current
    DESCRIPTION 	"Stuck bits in HD SDI Y channel data."

    ::= { sdistat 24 }


sdiCStuckbits   OBJECT-TYPE
    SYNTAX 	DisplayString
    MAX-ACCESS 	read-only
    STATUS 	current
    DESCRIPTION 	"Stuck bits in HD SDI C channel data."

    ::= { sdistat 25 }


sdiYCrcErrSecs  OBJECT-TYPE
    SYNTAX 	INTEGER
    MAX-ACCESS 	read-only
    STATUS 	current
    DESCRIPTION 	" Y CRC Errored Seconds."

    ::= { sdistat 26 }


sdiYCrcErrField OBJECT-TYPE
    SYNTAX 	INTEGER
    MAX-ACCESS 	read-only
    STATUS 	current
    DESCRIPTION 	"Y CRC Errored Fields."

    ::= { sdistat 27 }


sdiYCrcPctErrField OBJECT-TYPE
    SYNTAX 	DisplayString
    MAX-ACCESS 	read-only
    STATUS 	current
    DESCRIPTION 	"Y CRC Percent Errored Fields."

    ::= { sdistat 28 }


sdiCCrcErrSecs  OBJECT-TYPE
    SYNTAX 	INTEGER
    MAX-ACCESS 	read-only
    STATUS 	current
    DESCRIPTION 	" C CRC Errored Seconds."

    ::= { sdistat 29 }


sdiCCrcErrField OBJECT-TYPE
    SYNTAX 	INTEGER
    MAX-ACCESS 	read-only
    STATUS 	current
    DESCRIPTION 	"C CRC Errored Fields."

    ::= { sdistat 30 }


sdiCCrcPctErrField OBJECT-TYPE
    SYNTAX 	DisplayString
    MAX-ACCESS 	read-only
    STATUS 	current
    DESCRIPTION 	"C CRC Percent Errored Fields."

    ::= { sdistat 31 }


sdiYAncCksmErrSecs OBJECT-TYPE
    SYNTAX 	INTEGER
    MAX-ACCESS 	read-only
    STATUS 	current
    DESCRIPTION 	" Y Anc Checksum Errored Seconds."

    ::= { sdistat 32 }


sdiYAncCksmErrField OBJECT-TYPE
    SYNTAX 	INTEGER
    MAX-ACCESS 	read-only
    STATUS 	current
    DESCRIPTION 	"Y Anc Checksum Errored Fields."

    ::= { sdistat 33 }


sdiYAncCksmPctErrField OBJECT-TYPE
    SYNTAX 	DisplayString
    MAX-ACCESS 	read-only
    STATUS 	current
    DESCRIPTION 	"Y Anc Checksum Percent Errored Fields."

    ::= { sdistat 34 }


sdiCAncCksmErrSecs OBJECT-TYPE
    SYNTAX 	INTEGER
    MAX-ACCESS 	read-only
    STATUS 	current
    DESCRIPTION 	" C Anc Checksum Errored Seconds."

    ::= { sdistat 35 }


sdiCAncCksmErrField OBJECT-TYPE
    SYNTAX 	INTEGER
    MAX-ACCESS 	read-only
    STATUS 	current
    DESCRIPTION 	"C Anc Checksum Errored Fields."

    ::= { sdistat 36 }


sdiCAncCksmPctErrField OBJECT-TYPE
    SYNTAX 	DisplayString
    MAX-ACCESS 	read-only
    STATUS 	current
    DESCRIPTION 	"C Anc Checksum Percent Errored Fields."

    ::= { sdistat 37 }


vidSessionRuntime OBJECT-TYPE
    SYNTAX 	DisplayString
    MAX-ACCESS 	read-only
    STATUS 	current
    DESCRIPTION 	"Video Session Run Time."

    ::= { sdistat 38 }


eyeAmplitude    OBJECT-TYPE
    SYNTAX 	INTEGER
    MAX-ACCESS 	read-only
    STATUS 	current
    DESCRIPTION 	"Eye Signal Amplitude (mV."

    ::= { sdistat 39 }


eyeAmplMaxSD    OBJECT-TYPE
    SYNTAX 	INTEGER (700..1010)
    MAX-ACCESS 	read-write
    STATUS 	current
    DESCRIPTION 	"Eye Signal Amplitude Alarm upper threshold(mV)."

    ::= { sdistat 40 }


eyeAmplMinSD    OBJECT-TYPE
    SYNTAX 	INTEGER (550..1010)
    MAX-ACCESS 	read-write
    STATUS 	current
    DESCRIPTION 	"Eye Signal Amplitude Alarm lower threshold(mV)."

    ::= { sdistat 41 }


eyeAmplMaxHD    OBJECT-TYPE
    SYNTAX 	INTEGER (700..1010)
    MAX-ACCESS 	read-write
    STATUS 	current
    DESCRIPTION 	"Eye HD Signal Amplitude Alarm upper threshold(mV)."

    ::= { sdistat 42 }


eyeAmplMinHD    OBJECT-TYPE
    SYNTAX 	INTEGER (550..1010)
    MAX-ACCESS 	read-write
    STATUS 	current
    DESCRIPTION 	"Eye HD Signal Amplitude Alarm lower threshold(mV)."

    ::= { sdistat 43 }


eyeRiseTime     OBJECT-TYPE
    SYNTAX 	DisplayString
    MAX-ACCESS 	read-only
    STATUS 	current
    DESCRIPTION 	"Eye Signal RiseTime (nanoseconds)."

    ::= { sdistat 44 }


eyeRiseMaxSD    OBJECT-TYPE
    SYNTAX 	INTEGER (0..3000)
    MAX-ACCESS 	read-write
    STATUS 	current
    DESCRIPTION 	"Eye Signal RiseTime Alarm upper threshold (ps)."

    ::= { sdistat 45 }


eyeRiseMinSD    OBJECT-TYPE
    SYNTAX 	INTEGER (0..3000)
    MAX-ACCESS 	read-write
    STATUS 	current
    DESCRIPTION 	"Eye Signal RiseTime Alarm lower threshold(ps)."

    ::= { sdistat 46 }


eyeRiseMaxHD    OBJECT-TYPE
    SYNTAX 	INTEGER (0..1000)
    MAX-ACCESS 	read-write
    STATUS 	current
    DESCRIPTION 	"Eye HD Signal RiseTime Alarm upper threshold(ps)."

    ::= { sdistat 47 }


eyeRiseMinHD    OBJECT-TYPE
    SYNTAX 	INTEGER (0..1000)
    MAX-ACCESS 	read-write
    STATUS 	current
    DESCRIPTION 	"Eye HD Signal RiseTime Alarm lower threshold(ps)."

    ::= { sdistat 48 }


eyeFallTime     OBJECT-TYPE
    SYNTAX 	DisplayString
    MAX-ACCESS 	read-only
    STATUS 	current
    DESCRIPTION 	"Eye Signal FallTime (nanoseconds)."

    ::= { sdistat 49 }


eyeFallMaxSD    OBJECT-TYPE
    SYNTAX 	INTEGER (0..3000)
    MAX-ACCESS 	read-write
    STATUS 	current
    DESCRIPTION 	"Eye Signal FallTime Alarm upper threshold (ps)"

    ::= { sdistat 50 }


eyeFallMinSD    OBJECT-TYPE
    SYNTAX 	INTEGER (0..3000)
    MAX-ACCESS 	read-write
    STATUS 	current
    DESCRIPTION 	"Eye Signal FallTime Alarm lower threshold (ps)."

    ::= { sdistat 51 }


eyeFallMaxHD    OBJECT-TYPE
    SYNTAX 	INTEGER (0..1000)
    MAX-ACCESS 	read-write
    STATUS 	current
    DESCRIPTION 	"Eye Signal FallTime Alarm upper threshold (ps)."

    ::= { sdistat 52 }


eyeFallMinHD    OBJECT-TYPE
    SYNTAX 	INTEGER (0..1000)
    MAX-ACCESS 	read-write
    STATUS 	current
    DESCRIPTION 	"Eye Signal FallTime Alarm lower threshold (ps)."

    ::= { sdistat 53 }


eyeRiseFallDelta OBJECT-TYPE
    SYNTAX 	DisplayString
    MAX-ACCESS 	read-only
    STATUS 	current
    DESCRIPTION 	"Eye Delta (nanoseconds)."

    ::= { sdistat 54 }


eyeRiseFallMaxSD OBJECT-TYPE
    SYNTAX 	INTEGER (0..1000)
    MAX-ACCESS 	read-write
    STATUS 	current
    DESCRIPTION 	"Eye signal rise-fall Delta alarm threshold (ps)."

    ::= { sdistat 55 }


eyeRiseFallMaxHD OBJECT-TYPE
    SYNTAX 	INTEGER (0..1000)
    MAX-ACCESS 	read-write
    STATUS 	current
    DESCRIPTION 	"Eye HD signal rise-fall Delta alarm threshold (ps)."

    ::= { sdistat 56 }


eyeRiseOvershoot OBJECT-TYPE
    SYNTAX 	DisplayString
    MAX-ACCESS 	read-only
    STATUS 	current
    DESCRIPTION 	"Eye Signal Overshoot (percentage."

    ::= { sdistat 57 }


eyeRiseOvrMaxSD OBJECT-TYPE
    SYNTAX 	INTEGER (0..20)
    MAX-ACCESS 	read-write
    STATUS 	current
    DESCRIPTION 	"Eye Signal Rise Overshoot Alarm threshold(percentage)."

    ::= { sdistat 58 }


eyeRiseOvrMaxHD OBJECT-TYPE
    SYNTAX 	INTEGER (0..20)
    MAX-ACCESS 	read-write
    STATUS 	current
    DESCRIPTION 	"Eye HD Signal Rise Overshoot Alarm threshold(percentage)."

    ::= { sdistat 59 }


eyeFallOvershoot OBJECT-TYPE
    SYNTAX 	DisplayString
    MAX-ACCESS 	read-only
    STATUS 	current
    DESCRIPTION 	"Eye Signal Undershoot (percentage)."

    ::= { sdistat 60 }


eyeFallOvrMaxSD OBJECT-TYPE
    SYNTAX 	INTEGER (0..20)
    MAX-ACCESS 	read-write
    STATUS 	current
    DESCRIPTION 	"Eye Signal Fall Overshoot Alarm threshold(percentage)."

    ::= { sdistat 61 }


eyeFallOvrMaxHD OBJECT-TYPE
    SYNTAX 	INTEGER (0..20)
    MAX-ACCESS 	read-write
    STATUS 	current
    DESCRIPTION 	"Eye HD Signal Fall Overshoot Alarm threshold(percentage)."

    ::= { sdistat 62 }


eyeAmplMax3G    OBJECT-TYPE
    SYNTAX 	INTEGER (700..1010)
    MAX-ACCESS 	read-write
    STATUS 	current
    DESCRIPTION 	"Eye 3G Signal Amplitude Alarm upper Threshold(mv)."

    ::= { sdistat 63 }


eyeAmplMin3G    OBJECT-TYPE
    SYNTAX 	INTEGER (550..1010)
    MAX-ACCESS 	read-write
    STATUS 	current
    DESCRIPTION 	"Eye 3G Signal Amplitude Alarm lower Threshold(mv)."

    ::= { sdistat 64 }


eyeRiseMax3G    OBJECT-TYPE
    SYNTAX 	INTEGER (0..1000)
    MAX-ACCESS 	read-write
    STATUS 	current
    DESCRIPTION 	"Eye 3G Signal RiseTime Alarm upper threshold(ps)."

    ::= { sdistat 65 }


eyeRiseMin3G    OBJECT-TYPE
    SYNTAX 	INTEGER (0..1000)
    MAX-ACCESS 	read-write
    STATUS 	current
    DESCRIPTION 	"Eye 3G Signal RiseTime Alarm lower threshold(ps)."

    ::= { sdistat 66 }


eyeFallMax3G    OBJECT-TYPE
    SYNTAX 	INTEGER (0..1000)
    MAX-ACCESS 	read-write
    STATUS 	current
    DESCRIPTION 	"Eye 3G Signal FallTime Alarm upper threshold(ps)."

    ::= { sdistat 67 }


eyeFallMin3G    OBJECT-TYPE
    SYNTAX 	INTEGER (0..1000)
    MAX-ACCESS 	read-write
    STATUS 	current
    DESCRIPTION 	"Eye 3G Signal FallTime Alarm lower threshold(ps)."

    ::= { sdistat 68 }


eyeRiseFallMax3G OBJECT-TYPE
    SYNTAX 	INTEGER (0..1000)
    MAX-ACCESS 	read-write
    STATUS 	current
    DESCRIPTION 	"Eye 3G signal rise-fall Delta alarm threshold (ps)."

    ::= { sdistat 69 }


eyeRiseOvrMax3G OBJECT-TYPE
    SYNTAX 	INTEGER (0..20)
    MAX-ACCESS 	read-write
    STATUS 	current
    DESCRIPTION 	"Eye 3G Signal Rise Overshoot Alarm threshold(percentage)."

    ::= { sdistat 70 }


eyeFallOvrMax3G OBJECT-TYPE
    SYNTAX 	INTEGER (0..20)
    MAX-ACCESS 	read-write
    STATUS 	current
    DESCRIPTION 	"Eye 3G Signal Fall Overshoot Alarm threshold(percentage)."

    ::= { sdistat 71 }


hdCrcChange     OBJECT-TYPE
    SYNTAX 	INTEGER
    MAX-ACCESS 	read-only
    STATUS 	current
    DESCRIPTION 	"Returns HD Crc change status. Returns 0 for No Change, 1 for Change"

    ::= { sdistat 72 }


hdYCrcLinkA     OBJECT-TYPE
    SYNTAX 	INTEGER
    MAX-ACCESS 	read-only
    STATUS 	current
    DESCRIPTION 	"CRC of Luma Stream Single link HD or Link A of Dual Link"

    ::= { hdCrcEntry 1 }


hdCCrcLinkA     OBJECT-TYPE
    SYNTAX 	INTEGER
    MAX-ACCESS 	read-only
    STATUS 	current
    DESCRIPTION 	"CRC of Chroma Stream Single link HD or Link A of Dual Link"

    ::= { hdCrcEntry 2 }


hdYCrcLinkB     OBJECT-TYPE
    SYNTAX 	INTEGER
    MAX-ACCESS 	read-only
    STATUS 	current
    DESCRIPTION 	"CRC of Luma Stream Single link HD or Link B of Dual Link"

    ::= { hdCrcEntry 3 }


hdCCrcLinkB     OBJECT-TYPE
    SYNTAX 	INTEGER
    MAX-ACCESS 	read-only
    STATUS 	current
    DESCRIPTION 	"CRC of Chroma Stream Single link HD or Link B of Dual Link"

    ::= { hdCrcEntry 4 }


hdCrcTable      OBJECT-TYPE
    SYNTAX 	SEQUENCE OF HdCrcEntry
    MAX-ACCESS 	not-accessible
    STATUS 	current
    DESCRIPTION 	"Table for HD CRC"

    ::= { sdistat 73 }


hdCrcEntry      OBJECT-TYPE
    SYNTAX 	HdCrcEntry
    MAX-ACCESS 	not-accessible
    STATUS 	current
    DESCRIPTION 	"A row in the HD CRC Table table "
    INDEX { currChan }

    ::= { hdCrcTable 1 }


HdCrcEntry ::= SEQUENCE {
    hdYCrcLinkA 	INTEGER,
    hdCCrcLinkA 	INTEGER,
    hdYCrcLinkB 	INTEGER,
    hdCCrcLinkB 	INTEGER 
}

sdi4KErrorTableIndex OBJECT-TYPE
    SYNTAX 	INTEGER {
        a(0),
        b(1),
        c(2),
        d(3)
    }
    MAX-ACCESS 	not-accessible
    STATUS 	current
    DESCRIPTION 	"Sdi4k Error Table Index.  This variable is an index for sdi4kErrorTable"

    ::= { sdistat 74 }


sdi352Payload4K OBJECT-TYPE
    SYNTAX 	DisplayString
    MAX-ACCESS 	read-only
    STATUS 	current
    DESCRIPTION 	"SDI 352 payload value of Quad-HD, Quad-3GB."

    ::= { sdi4KErrorTableEntry 1 }


sdiYStuckbits4K OBJECT-TYPE
    SYNTAX 	DisplayString
    MAX-ACCESS 	read-only
    STATUS 	current
    DESCRIPTION 	"Stuck bits in Quad-HD, Quad-3GB SDI Y channel data."

    ::= { sdi4KErrorTableEntry 2 }


sdiCStuckbits4K OBJECT-TYPE
    SYNTAX 	DisplayString
    MAX-ACCESS 	read-only
    STATUS 	current
    DESCRIPTION 	"Stuck bits in Quad-HD, Quad-3GB SDI C channel data."

    ::= { sdi4KErrorTableEntry 3 }


hdYCrcLinkA4K   OBJECT-TYPE
    SYNTAX 	INTEGER
    MAX-ACCESS 	read-only
    STATUS 	current
    DESCRIPTION 	"CRC of Luma Stream Quad link HD or Link A of Quad Link 3GB "

    ::= { sdi4KErrorTableEntry 4 }


hdCCrcLinkA4K   OBJECT-TYPE
    SYNTAX 	INTEGER
    MAX-ACCESS 	read-only
    STATUS 	current
    DESCRIPTION 	"CRC of Chroma Stream Quad link HD or Link A of Quad Link 3GB "

    ::= { sdi4KErrorTableEntry 5 }


hdYCrcLinkB4K   OBJECT-TYPE
    SYNTAX 	INTEGER
    MAX-ACCESS 	read-only
    STATUS 	current
    DESCRIPTION 	"CRC of Luma Stream Quad link HD or Link B of Quad Link 3GB "

    ::= { sdi4KErrorTableEntry 6 }


hdCCrcLinkB4K   OBJECT-TYPE
    SYNTAX 	INTEGER
    MAX-ACCESS 	read-only
    STATUS 	current
    DESCRIPTION 	"CRC of Chroma Stream Quad link HD or Link B of Quad Link 3GB "

    ::= { sdi4KErrorTableEntry 7 }


fieldLengthError OBJECT-TYPE
    SYNTAX 	DisplayString
    MAX-ACCESS 	read-only
    STATUS 	current
    DESCRIPTION 	"Field Length Error of Link Signal."

    ::= { sdi4KErrorTableEntry 8 }


savPlaceError   OBJECT-TYPE
    SYNTAX 	DisplayString
    MAX-ACCESS 	read-only
    STATUS 	current
    DESCRIPTION 	"SAV Place Error of Link Signal."

    ::= { sdi4KErrorTableEntry 9 }


lineLengthError OBJECT-TYPE
    SYNTAX 	DisplayString
    MAX-ACCESS 	read-only
    STATUS 	current
    DESCRIPTION 	"Line Length Error of Link Signal."

    ::= { sdi4KErrorTableEntry 10 }


lineNumberError OBJECT-TYPE
    SYNTAX 	DisplayString
    MAX-ACCESS 	read-only
    STATUS 	current
    DESCRIPTION 	"Line Number Error of Link Signal."

    ::= { sdi4KErrorTableEntry 11 }


ancillayrDataPresence OBJECT-TYPE
    SYNTAX 	DisplayString
    MAX-ACCESS 	read-only
    STATUS 	current
    DESCRIPTION 	"Ancillary Data in Link Signal."

    ::= { sdi4KErrorTableEntry 12 }


sdi4KErrorTable OBJECT-TYPE
    SYNTAX 	SEQUENCE OF Sdi4KErrorTableEntry
    MAX-ACCESS 	not-accessible
    STATUS 	current
    DESCRIPTION 	"Table for sdi 4K-CRC, Stuck bits info, 352M Payload info, Errors "

    ::= { sdistat 75 }


sdi4KErrorTableEntry OBJECT-TYPE
    SYNTAX 	Sdi4KErrorTableEntry
    MAX-ACCESS 	not-accessible
    STATUS 	current
    DESCRIPTION 	"A row in the sdi4kErrorTable table "
    INDEX { sdi4KErrorTableIndex }

    ::= { sdi4KErrorTable 1 }


Sdi4KErrorTableEntry ::= SEQUENCE {
    sdi352Payload4K 	DisplayString,
    sdiYStuckbits4K 	DisplayString,
    sdiCStuckbits4K 	DisplayString,
    hdYCrcLinkA4K 	INTEGER,
    hdCCrcLinkA4K 	INTEGER,
    hdYCrcLinkB4K 	INTEGER,
    hdCCrcLinkB4K 	INTEGER,
    fieldLengthError 	DisplayString,
    savPlaceError 	DisplayString,
    lineLengthError 	DisplayString,
    lineNumberError 	DisplayString,
    ancillayrDataPresence 	DisplayString 
}
-- 
-- preset group
-- Preset control variables.

presetLoad      OBJECT-TYPE
    SYNTAX 	INTEGER (-1..32)
    MAX-ACCESS 	read-write
    STATUS 	current
    DESCRIPTION 	"Recall/Load the preset configuration from instrument non-volatile storage.  Factory preset is preset number 0.  User presets start at preset number 1. (write only)."

    ::= { preset 1 }


presetSave      OBJECT-TYPE
    SYNTAX 	INTEGER (1..32)
    MAX-ACCESS 	read-write
    STATUS 	current
    DESCRIPTION 	"Save the current settings to one of user preset storage locations in instrument non-volatile storage.  User presets start at location number 1. (write only)."

    ::= { preset 2 }


presetLoadProgress OBJECT-TYPE
    SYNTAX 	INTEGER
    MAX-ACCESS 	read-only
    STATUS 	current
    DESCRIPTION 	"Indicates preset loading process progress (% of the restoring process completed)"

    ::= { preset 3 }


presetRemove    OBJECT-TYPE
    SYNTAX 	INTEGER (1..32)
    MAX-ACCESS 	read-write
    STATUS 	current
    DESCRIPTION 	"Delete the preset from instrument (write only) "

    ::= { preset 4 }


presetNum       OBJECT-TYPE
    SYNTAX 	INTEGER (0..31)
    MAX-ACCESS 	not-accessible
    STATUS 	current
    DESCRIPTION 	"Preset number. This is used as index in preset table."

    ::= { preset 5 }


presetGroupNum  OBJECT-TYPE
    SYNTAX 	INTEGER {
        group1(0),
        group2(1),
        group3(2),
        group4(3)
    }
    MAX-ACCESS 	not-accessible
    STATUS 	current
    DESCRIPTION 	"Preset group number. This is used as index in preset group table."

    ::= { preset 6 }


presetName      OBJECT-TYPE
    SYNTAX 	DisplayString
    MAX-ACCESS 	read-write
    STATUS 	current
    DESCRIPTION 	"User-defined name of a preset."

    ::= { presetEntry 1 }


presetValid     OBJECT-TYPE
    SYNTAX 	INTEGER {
        no(0),
        yes(1)
    }
    MAX-ACCESS 	read-only
    STATUS 	current
    DESCRIPTION 	"This indicates whether the preset is empty or it is a valid one(which can be restored)."

    ::= { presetEntry 2 }


presetTable     OBJECT-TYPE
    SYNTAX 	SEQUENCE OF PresetEntry
    MAX-ACCESS 	not-accessible
    STATUS 	current
    DESCRIPTION 	"Table for preset inforamtion."

    ::= { preset 7 }


presetEntry     OBJECT-TYPE
    SYNTAX 	PresetEntry
    MAX-ACCESS 	not-accessible
    STATUS 	current
    DESCRIPTION 	"a row in the preset table"
    INDEX { presetNum }

    ::= { presetTable 1 }


PresetEntry ::= SEQUENCE {
    presetName 	DisplayString,
    presetValid 	INTEGER 
}

presetGroupName OBJECT-TYPE
    SYNTAX 	DisplayString
    MAX-ACCESS 	read-write
    STATUS 	current
    DESCRIPTION 	"User-defined name of a preset group."

    ::= { presetGroupEntry 1 }


presetGroupTable OBJECT-TYPE
    SYNTAX 	SEQUENCE OF PresetGroupEntry
    MAX-ACCESS 	not-accessible
    STATUS 	current
    DESCRIPTION 	"Table for preset group inforamtion."

    ::= { preset 8 }


presetGroupEntry OBJECT-TYPE
    SYNTAX 	PresetGroupEntry
    MAX-ACCESS 	not-accessible
    STATUS 	current
    DESCRIPTION 	"a row in the preset group table"
    INDEX { presetGroupNum }

    ::= { presetGroupTable 1 }


PresetGroupEntry ::= SEQUENCE {
    presetGroupName 	DisplayString 
}
-- 
-- gamut Group
-- Gamut threshold and control variables

arrNtscThrHigh  OBJECT-TYPE
    SYNTAX 	INTEGER
    MAX-ACCESS 	read-write
    STATUS 	current
    DESCRIPTION 	"Upper threshold of NTSC composite signal (IRE units)."

    ::= { gamut 1 }


arrPalThrHigh   OBJECT-TYPE
    SYNTAX 	INTEGER
    MAX-ACCESS 	read-write
    STATUS 	current
    DESCRIPTION 	"Upper threshold of PAL composite signal (mV)."

    ::= { gamut 2 }


arrPalThrLow    OBJECT-TYPE
    SYNTAX 	INTEGER
    MAX-ACCESS 	read-write
    STATUS 	current
    DESCRIPTION 	"Lower threshold of PAL composite signal (mV)."

    ::= { gamut 3 }


arrThrArea      OBJECT-TYPE
    SYNTAX 	INTEGER
    MAX-ACCESS 	read-write
    STATUS 	current
    DESCRIPTION 	"Arrowhead threshold area (% of active picture area)."

    ::= { gamut 4 }


lumaThrHigh     OBJECT-TYPE
    SYNTAX 	DisplayString
    MAX-ACCESS 	read-write
    STATUS 	current
    DESCRIPTION 	"Upper luma threshold ( % of white level)."

    ::= { gamut 5 }


lumaThrLow      OBJECT-TYPE
    SYNTAX 	DisplayString
    MAX-ACCESS 	read-write
    STATUS 	current
    DESCRIPTION 	"Lower luma threshold ( % of white level relative to black)."

    ::= { gamut 6 }


lumaThrArea     OBJECT-TYPE
    SYNTAX 	INTEGER
    MAX-ACCESS 	read-write
    STATUS 	current
    DESCRIPTION 	"Luma threshold area (% of active picture area)."

    ::= { gamut 7 }


arrNtscThrLow   OBJECT-TYPE
    SYNTAX 	INTEGER
    MAX-ACCESS 	read-write
    STATUS 	current
    DESCRIPTION 	"Lower threshold of NTSC composite signal (IRE units)."

    ::= { gamut 8 }


resetLumaDefault OBJECT-TYPE
    SYNTAX 	INTEGER {
        ready(0),
        reset(1)
    }
    MAX-ACCESS 	read-write
    STATUS 	current
    DESCRIPTION 	"Reset Luma thresholds to default values(write only)."

    ::= { gamut 9 }


resetEBU-R103Default OBJECT-TYPE
    SYNTAX 	INTEGER {
        ready(0),
        reset(1)
    }
    MAX-ACCESS 	read-write
    STATUS 	current
    DESCRIPTION 	"Reset Gamut thresholds to EBU-R103 default values(write only)."

    ::= { gamut 10 }


dmdThrHigh      OBJECT-TYPE
    SYNTAX 	INTEGER
    MAX-ACCESS 	read-write
    STATUS 	current
    DESCRIPTION 	"RGB gamut upper threshold (mV)."

    ::= { gamut 11 }


dmdThrLow       OBJECT-TYPE
    SYNTAX 	INTEGER
    MAX-ACCESS 	read-write
    STATUS 	current
    DESCRIPTION 	"RGB gamut lower threshold (mV)."

    ::= { gamut 12 }


dmdThrArea      OBJECT-TYPE
    SYNTAX 	INTEGER
    MAX-ACCESS 	read-write
    STATUS 	current
    DESCRIPTION 	"RGB gamut threshold area (% of active picture area)."

    ::= { gamut 13 }


resetTEKDefault OBJECT-TYPE
    SYNTAX 	INTEGER {
        reset(1)
    }
    MAX-ACCESS 	read-write
    STATUS 	current
    DESCRIPTION 	"Reset thresholds to TEK default thresholds(write only)."

    ::= { gamut 14 }


rgbGamutFilter  OBJECT-TYPE
    SYNTAX 	INTEGER {
        horizontal(0),
        horzPlusVert(1)
    }
    MAX-ACCESS 	read-write
    STATUS 	current
    DESCRIPTION 	"RGB gamut filter selection."

    ::= { gamut 15 }


cpstGamutFilter OBJECT-TYPE
    SYNTAX 	INTEGER {
        horizontal(0),
        horzPlusVert(1)
    }
    MAX-ACCESS 	read-write
    STATUS 	current
    DESCRIPTION 	"Composite gamut filter selection."

    ::= { gamut 16 }


lumaGamutFilter OBJECT-TYPE
    SYNTAX 	INTEGER {
        horizontal(0),
        horzPlusVert(1)
    }
    MAX-ACCESS 	read-write
    STATUS 	current
    DESCRIPTION 	"Luma gamut filter selection."

    ::= { gamut 17 }

-- 
-- eye group
-- Eye pattern mode variables

eyeHorPos       OBJECT-TYPE
    SYNTAX 	DisplayString
    MAX-ACCESS 	read-write
    STATUS 	current
    DESCRIPTION 	"Horizontal position of eye pattern. Range -1.0 to +1.0."

    ::= { eyeEntry 1 }


eyeVertPos      OBJECT-TYPE
    SYNTAX 	DisplayString
    MAX-ACCESS 	read-write
    STATUS 	current
    DESCRIPTION 	"vertical position of eye pattern,Range -1800 mv to +1800 mv"

    ::= { eyeEntry 2 }


eyeSweepMode    OBJECT-TYPE
    SYNTAX 	INTEGER {
        h1(1),
        h2(2),
        f1(3),
        f2(4)
    }
    MAX-ACCESS 	read-write
    STATUS 	current
    DESCRIPTION 	"Sweep mode of eye pattern display"

    ::= { eyeEntry 3 }


eyeGainMode     OBJECT-TYPE
    SYNTAX 	INTEGER {
        gain-x1(0),
        gain-x5(1),
        gain-x10(2),
        gain-x2(3)
    }
    MAX-ACCESS 	read-write
    STATUS 	current
    DESCRIPTION 	"Fixed gain for eye pattern display"

    ::= { eyeEntry 4 }


eyeVarGainEnable OBJECT-TYPE
    SYNTAX 	INTEGER {
        off(0),
        on(1)
    }
    MAX-ACCESS 	read-write
    STATUS 	current
    DESCRIPTION 	"Enable/disable variable gain for eye pattern display"

    ::= { eyeEntry 5 }


eyeVarGain      OBJECT-TYPE
    SYNTAX 	DisplayString
    MAX-ACCESS 	read-write
    STATUS 	current
    DESCRIPTION 	"Variable gain for eye pattern display (effective).  Range of values depend on current value of eyeGainMode."

    ::= { eyeEntry 6 }


eyeCursorMode   OBJECT-TYPE
    SYNTAX 	INTEGER {
        volt(0),
        time(1),
        voltAndTime(2)
    }
    MAX-ACCESS 	read-write
    STATUS 	current
    DESCRIPTION 	"Cursor mode for eye pattern display"

    ::= { eyeEntry 7 }


eyeCursorActive OBJECT-TYPE
    SYNTAX 	INTEGER {
        off(0),
        on(1)
    }
    MAX-ACCESS 	read-write
    STATUS 	current
    DESCRIPTION 	"Enable/disable cursors in Eye display mode"

    ::= { eyeEntry 8 }


eyeCursorH1Pos  OBJECT-TYPE
    SYNTAX 	DisplayString
    MAX-ACCESS 	read-write
    STATUS 	current
    DESCRIPTION 	"Position of first horizontal cursor in eye pattern display."

    ::= { eyeEntry 9 }


eyeCursorH2Pos  OBJECT-TYPE
    SYNTAX 	DisplayString
    MAX-ACCESS 	read-write
    STATUS 	current
    DESCRIPTION 	"Position of second horizontal cursor in eye pattern display."

    ::= { eyeEntry 10 }


eyeCursorV1Pos  OBJECT-TYPE
    SYNTAX 	DisplayString
    MAX-ACCESS 	read-write
    STATUS 	current
    DESCRIPTION 	"Position of first vertical cursor in eye pattern display (mV)"

    ::= { eyeEntry 11 }


eyeCursorV2Pos  OBJECT-TYPE
    SYNTAX 	DisplayString
    MAX-ACCESS 	read-write
    STATUS 	current
    DESCRIPTION 	"Position of second vertical cursor in eye pattern display (mV)"

    ::= { eyeEntry 12 }


eyeCursorHDelta OBJECT-TYPE
    SYNTAX 	DisplayString
    MAX-ACCESS 	read-write
    STATUS 	current
    DESCRIPTION 	"Voltage difference between horizontal cursors in eye display mode"

    ::= { eyeEntry 13 }


eyeCursorVDelta OBJECT-TYPE
    SYNTAX 	DisplayString
    MAX-ACCESS 	read-write
    STATUS 	current
    DESCRIPTION 	"Voltage difference between Vertical cursors in eye display mode"

    ::= { eyeEntry 14 }


eyeHMag         OBJECT-TYPE
    SYNTAX 	INTEGER {
        off(0),
        on(1),
        gain-x2(2),
        gain-x5(5),
        gain-x10(10)
    }
    MAX-ACCESS 	read-write
    STATUS 	current
    DESCRIPTION 	"Enable/disable horizontal magnification in eye pattern display"

    ::= { eyeEntry 15 }


eyeCenter       OBJECT-TYPE
    SYNTAX 	INTEGER {
        off(0),
        on(1)
    }
    MAX-ACCESS 	read-write
    STATUS 	current
    DESCRIPTION 	"Center Eye pattern (write only)"

    ::= { eyeEntry 16 }


eyeNumEyes      OBJECT-TYPE
    SYNTAX 	INTEGER {
        eye3(0),
        eye10(1),
        eye20(2)
    }
    MAX-ACCESS 	read-write
    STATUS 	current
    DESCRIPTION 	"Number of eyes in eye pattern"

    ::= { eyeEntry 18 }


eyeDcOffset     OBJECT-TYPE
    SYNTAX 	INTEGER
    MAX-ACCESS 	read-only
    STATUS 	current
    DESCRIPTION 	"Eye DC Offset (mV)"

    ::= { eyeEntry 25 }


eyePercentCurUnits OBJECT-TYPE
    SYNTAX 	INTEGER {
        mv(0),
        percent(1)
    }
    MAX-ACCESS 	read-write
    STATUS 	current
    DESCRIPTION 	"Units of measure for vertical cursors in Eye display mode"

    ::= { eyeEntry 26 }


eyeOneOverTCurUnits OBJECT-TYPE
    SYNTAX 	INTEGER {
        sec(0),
        oneOverT(1)
    }
    MAX-ACCESS 	read-write
    STATUS 	current
    DESCRIPTION 	"Units of measure for horizontal cursor delta as time or 1/t"

    ::= { eyeEntry 27 }


eyeSetCur100Percent OBJECT-TYPE
    SYNTAX 	INTEGER
    MAX-ACCESS 	read-write
    STATUS 	current
    DESCRIPTION 	"Sets current vertical cursor positions as 0% and 100% reference levels for Eye mode display (write-only)"

    ::= { eyeEntry 28 }


eyeFixedHMag    OBJECT-TYPE
    SYNTAX 	INTEGER {
        gain-x1(0),
        gain-x2(1),
        gain-x5(2),
        gain-x10(3)
    }
    MAX-ACCESS 	read-write
    STATUS 	deprecated
    DESCRIPTION 	"Horizontal fixed magnification value in eye display mode"

    ::= { eyeEntry 29 }


eyeMeterDisplay OBJECT-TYPE
    SYNTAX 	INTEGER {
        off(0),
        meter-only(1),
        readout-only(2),
        meter-and-readout(3)
    }
    MAX-ACCESS 	read-write
    STATUS 	current
    DESCRIPTION 	"Jitter meter and readout display in Eye mode"

    ::= { eyeEntry 30 }


eyeTimePerDiv   OBJECT-TYPE
    SYNTAX 	DisplayString
    MAX-ACCESS 	read-only
    STATUS 	current
    DESCRIPTION 	"The time per division of the eye trace."

    ::= { eyeEntry 31 }


eyeTable        OBJECT-TYPE
    SYNTAX 	SEQUENCE OF EyeEntry
    MAX-ACCESS 	not-accessible
    STATUS 	current
    DESCRIPTION 	"Table for eye display mode"

    ::= { eye 1 }


eyeEntry        OBJECT-TYPE
    SYNTAX 	EyeEntry
    MAX-ACCESS 	not-accessible
    STATUS 	current
    DESCRIPTION 	"A row in the eye table "
    INDEX { currTile }

    ::= { eyeTable 1 }


EyeEntry ::= SEQUENCE {
    eyeHorPos 	DisplayString,
    eyeVertPos 	DisplayString,
    eyeSweepMode 	INTEGER,
    eyeGainMode 	INTEGER,
    eyeVarGainEnable 	INTEGER,
    eyeVarGain 	DisplayString,
    eyeCursorMode 	INTEGER,
    eyeCursorActive 	INTEGER,
    eyeCursorH1Pos 	DisplayString,
    eyeCursorH2Pos 	DisplayString,
    eyeCursorV1Pos 	DisplayString,
    eyeCursorV2Pos 	DisplayString,
    eyeCursorHDelta 	DisplayString,
    eyeCursorVDelta 	DisplayString,
    eyeHMag 	INTEGER,
    eyeCenter 	INTEGER,
    eyeNumEyes 	INTEGER,
    eyeDcOffset 	INTEGER,
    eyePercentCurUnits 	INTEGER,
    eyeOneOverTCurUnits 	INTEGER,
    eyeSetCur100Percent 	INTEGER,
    eyeFixedHMag 	INTEGER,
    eyeMeterDisplay 	INTEGER,
    eyeTimePerDiv 	DisplayString 
}

eyeType         OBJECT-TYPE
    SYNTAX 	INTEGER {
        eye(0),
        equalized-eye(1)
    }
    MAX-ACCESS 	read-write
    STATUS 	current
    DESCRIPTION 	"Select the eye trace type."

    ::= { eye 2 }

--  eye 3 
--  eye 4 

eyeEqualizerBypass OBJECT-TYPE
    SYNTAX 	INTEGER {
        off(0),
        on(1)
    }
    MAX-ACCESS 	read-write
    STATUS 	current
    DESCRIPTION 	"Eye Equalise Bypass."

    ::= { eye 5 }


eyeShowMeasurements OBJECT-TYPE
    SYNTAX 	INTEGER {
        hide(0),
        show(1)
    }
    MAX-ACCESS 	read-write
    STATUS 	current
    DESCRIPTION 	"Show/hide eye measurements in Eye display."

    ::= { eye 6 }


eyeOutput       OBJECT-TYPE
    SYNTAX 	INTEGER {
        loopout-b(0),
        recovered-clock(1)
    }
    MAX-ACCESS 	read-write
    STATUS 	current
    DESCRIPTION 	"Configure the output on eye board as either loop B output or recovered clock output."

    ::= { eye 7 }

-- 
-- jitter group
-- Jitter display mode variables

jitHorPos       OBJECT-TYPE
    SYNTAX 	DisplayString
    MAX-ACCESS 	read-write
    STATUS 	current
    DESCRIPTION 	"Horizontal position of jitter waveform. Range -1.0 to +1.0."

    ::= { jitEntry 1 }


jitVertPos      OBJECT-TYPE
    SYNTAX 	DisplayString
    MAX-ACCESS 	read-write
    STATUS 	current
    DESCRIPTION 	"vertical position of jitter pattern, Range -10 UI to +10 UI"

    ::= { jitEntry 2 }


jitSweepMode    OBJECT-TYPE
    SYNTAX 	INTEGER {
        h1(1),
        h2(2),
        f1(3),
        f2(4)
    }
    MAX-ACCESS 	read-write
    STATUS 	current
    DESCRIPTION 	"Sweep mode of jitter waveform"

    ::= { jitEntry 3 }


jitGainMode     OBJECT-TYPE
    SYNTAX 	INTEGER {
        gain-x1(0),
        gain-x5(1),
        gain-x10(2),
        gain-x2(3)
    }
    MAX-ACCESS 	read-write
    STATUS 	current
    DESCRIPTION 	"Fixed gain for jitter  display mode"

    ::= { jitEntry 4 }


jitVarGainEnable OBJECT-TYPE
    SYNTAX 	INTEGER {
        off(0),
        on(1)
    }
    MAX-ACCESS 	read-write
    STATUS 	current
    DESCRIPTION 	"Enable/disable variable gain for jitter display mode"

    ::= { jitEntry 5 }


jitVarGain      OBJECT-TYPE
    SYNTAX 	DisplayString
    MAX-ACCESS 	read-write
    STATUS 	current
    DESCRIPTION 	"Variable gain for jitter display mode  Range of values depend on current value of jitGainMode."

    ::= { jitEntry 6 }


jitCursorMode   OBJECT-TYPE
    SYNTAX 	INTEGER {
        volt(0),
        time(1),
        voltAndTime(2)
    }
    MAX-ACCESS 	read-write
    STATUS 	current
    DESCRIPTION 	"Cursor mode for jitter display"

    ::= { jitEntry 7 }


jitCursorActive OBJECT-TYPE
    SYNTAX 	INTEGER {
        off(0),
        on(1)
    }
    MAX-ACCESS 	read-write
    STATUS 	current
    DESCRIPTION 	"Enable/disable cursors in Jitter display mode"

    ::= { jitEntry 8 }


jitCursorH1Pos  OBJECT-TYPE
    SYNTAX 	DisplayString
    MAX-ACCESS 	read-write
    STATUS 	current
    DESCRIPTION 	"Position of first horizontal cursor in jitter display mode."

    ::= { jitEntry 9 }


jitCursorH2Pos  OBJECT-TYPE
    SYNTAX 	DisplayString
    MAX-ACCESS 	read-write
    STATUS 	current
    DESCRIPTION 	"Position of second horizontal cursor in jitter display mode."

    ::= { jitEntry 10 }


jitCursorV1Pos  OBJECT-TYPE
    SYNTAX 	DisplayString
    MAX-ACCESS 	read-write
    STATUS 	current
    DESCRIPTION 	"Position of first vertical cursor in jitter display mode"

    ::= { jitEntry 11 }


jitCursorV2Pos  OBJECT-TYPE
    SYNTAX 	DisplayString
    MAX-ACCESS 	read-write
    STATUS 	current
    DESCRIPTION 	"Position of second vertical cursor in jitter display mode"

    ::= { jitEntry 12 }


jitCursorHDelta OBJECT-TYPE
    SYNTAX 	DisplayString
    MAX-ACCESS 	read-only
    STATUS 	current
    DESCRIPTION 	"Time difference between horizontal cursors in jitter display mode"

    ::= { jitEntry 13 }


jitCursorVDelta OBJECT-TYPE
    SYNTAX 	DisplayString
    MAX-ACCESS 	read-only
    STATUS 	current
    DESCRIPTION 	"Voltage difference between Vertical cursors in jitter display mode"

    ::= { jitEntry 14 }


jitHMag         OBJECT-TYPE
    SYNTAX 	INTEGER {
        off(0),
        on(1),
        gain-x10(10),
        gain-x20(20),
        gain-x25(25),
        gain-x50(50)
    }
    MAX-ACCESS 	read-write
    STATUS 	current
    DESCRIPTION 	"Enable/disable horizontal magnification in jitter display mode"

    ::= { jitEntry 15 }


jitCenter       OBJECT-TYPE
    SYNTAX 	INTEGER {
        off(0),
        on(1)
    }
    MAX-ACCESS 	read-write
    STATUS 	current
    DESCRIPTION 	"Center Jitter waveform (write only)"

    ::= { jitEntry 16 }


jitPercentCurUnits OBJECT-TYPE
    SYNTAX 	INTEGER {
        ui(0),
        percent(1)
    }
    MAX-ACCESS 	read-write
    STATUS 	current
    DESCRIPTION 	"Units of measure for vertical cursors in Jitter display mode"

    ::= { jitEntry 19 }


jitOneOverTCurUnits OBJECT-TYPE
    SYNTAX 	INTEGER {
        sec(0),
        oneOverT(1)
    }
    MAX-ACCESS 	read-write
    STATUS 	current
    DESCRIPTION 	"Units of measure for horizontal cursor delta as time or 1/t"

    ::= { jitEntry 20 }


jitSetCur100Percent OBJECT-TYPE
    SYNTAX 	INTEGER
    MAX-ACCESS 	read-write
    STATUS 	current
    DESCRIPTION 	"Sets current vertical cursor positions as 0% and 100% reference levels for Jitter mode display (write-only)"

    ::= { jitEntry 21 }


jitFixedHMag    OBJECT-TYPE
    SYNTAX 	INTEGER {
        gain-x1(0),
        gain-x10(1),
        gain-x20(2),
        gain-x50(3)
    }
    MAX-ACCESS 	read-write
    STATUS 	deprecated
    DESCRIPTION 	"Horizontal fixed magnification value in jitter display mode"

    ::= { jitEntry 22 }


jitMeterDisplay OBJECT-TYPE
    SYNTAX 	INTEGER {
        off(0),
        meter-only(1),
        readout-only(2),
        meter-and-readout(3)
    }
    MAX-ACCESS 	read-write
    STATUS 	current
    DESCRIPTION 	"Jitter meter and readout display in Jitter mode"

    ::= { jitEntry 23 }


jitTable        OBJECT-TYPE
    SYNTAX 	SEQUENCE OF JitEntry
    MAX-ACCESS 	not-accessible
    STATUS 	current
    DESCRIPTION 	"Table for Jitter display mode"

    ::= { jitter 1 }


jitEntry        OBJECT-TYPE
    SYNTAX 	JitEntry
    MAX-ACCESS 	not-accessible
    STATUS 	current
    DESCRIPTION 	"A row in the jitter table "
    INDEX { currTile }

    ::= { jitTable 1 }


JitEntry ::= SEQUENCE {
    jitHorPos 	DisplayString,
    jitVertPos 	DisplayString,
    jitSweepMode 	INTEGER,
    jitGainMode 	INTEGER,
    jitVarGainEnable 	INTEGER,
    jitVarGain 	DisplayString,
    jitCursorMode 	INTEGER,
    jitCursorActive 	INTEGER,
    jitCursorH1Pos 	DisplayString,
    jitCursorH2Pos 	DisplayString,
    jitCursorV1Pos 	DisplayString,
    jitCursorV2Pos 	DisplayString,
    jitCursorHDelta 	DisplayString,
    jitCursorVDelta 	DisplayString,
    jitHMag 	INTEGER,
    jitCenter 	INTEGER,
    jitPercentCurUnits 	INTEGER,
    jitOneOverTCurUnits 	INTEGER,
    jitSetCur100Percent 	INTEGER,
    jitFixedHMag 	INTEGER,
    jitMeterDisplay 	INTEGER 
}

smpte259ThrJitLvl OBJECT-TYPE
    SYNTAX 	JitterLevel (370..14800)
    MAX-ACCESS 	read-write
    STATUS 	current
    DESCRIPTION 	"Set the default jitter threshold level for each of the two jitter engines, for SMPTE 259(SD) signals. Row 1 is for jitter1 threshold level and row 2 is for jitter2 threshold level. Alarms are generated when this threshold is exceeded."

    ::= { jitMeasEntry 1 }


smpte292ThrJitLvl OBJECT-TYPE
    SYNTAX 	JitterLevel (67..2694)
    MAX-ACCESS 	read-write
    STATUS 	current
    DESCRIPTION 	"Set the default jitter threshold level for each of the two jitter engines, for SMPTE 292(HD) signals. Row 1 is for jitter1 threshold level and row 2 is for jitter2 threshold level. Alarms are generated when this threshold is exceeded."

    ::= { jitMeasEntry 2 }


jitHpf          OBJECT-TYPE
    SYNTAX 	INTEGER {
        alignment(-2),
        timing(-1),
        bw10Hz(1),
        bw100Hz(2),
        bw1KHz(3),
        bw10KHz(4),
        bw100KHz(5)
    }
    MAX-ACCESS 	read-write
    STATUS 	current
    DESCRIPTION 	"Jitter highpass filter bandwidth selection."

    ::= { jitMeasEntry 3 }


jitMeasurement  OBJECT-TYPE
    SYNTAX 	INTEGER
    MAX-ACCESS 	read-only
    STATUS 	current
    DESCRIPTION 	"Jitter measurement in ps "

    ::= { jitMeasEntry 4 }


smpte425ThrJitLvl OBJECT-TYPE
    SYNTAX 	JitterLevel (34..1360)
    MAX-ACCESS 	read-write
    STATUS 	current
    DESCRIPTION 	"Set the default jitter threshold level for each of the two jitter engines, for SMPTE 425(3G) signals. Row 1 is for jitter1 threshold level and row 2 is for jitter2 threshold level. Alarms are generated when this threshold is exceeded."

    ::= { jitMeasEntry 5 }


jitMeasTable    OBJECT-TYPE
    SYNTAX 	SEQUENCE OF JitMeasEntry
    MAX-ACCESS 	not-accessible
    STATUS 	current
    DESCRIPTION 	"Table for Jitter Measurement "

    ::= { jitter 2 }


jitMeasEntry    OBJECT-TYPE
    SYNTAX 	JitMeasEntry
    MAX-ACCESS 	not-accessible
    STATUS 	current
    DESCRIPTION 	"A row in the Jitter Measure table "
    INDEX { jitMeasEngine }

    ::= { jitMeasTable 1 }


JitMeasEntry ::= SEQUENCE {
    smpte259ThrJitLvl 	JitterLevel,
    smpte292ThrJitLvl 	JitterLevel,
    jitHpf 	INTEGER,
    jitMeasurement 	INTEGER,
    smpte425ThrJitLvl 	JitterLevel 
}

jitMeasEngine   OBJECT-TYPE
    SYNTAX 	INTEGER {
        engine1(0),
        engine2(1)
    }
    MAX-ACCESS 	not-accessible
    STATUS 	current
    DESCRIPTION 	"Currently Selected Jitter Measurement engine. This is used as index in jitrMeasTable."

    ::= { jitter 3 }


jitShowMeasurements OBJECT-TYPE
    SYNTAX 	INTEGER {
        hide(0),
        show(1)
    }
    MAX-ACCESS 	read-write
    STATUS 	current
    DESCRIPTION 	"Show/hide jitter measurements in Jitter display."

    ::= { jitter 4 }


t3gClockBw      OBJECT-TYPE
    SYNTAX 	INTEGER {
        narrow(0),
        wide(1)
    }
    MAX-ACCESS 	read-write
    STATUS 	current
    DESCRIPTION 	"Select the bandwidth of 3Gbps recovered clock output filter."

    ::= { jitter 5 }

-- 
-- logstat group
-- Event log control variables

logClear        OBJECT-TYPE
    SYNTAX 	INTEGER {
        ready(0),
        clear(1)
    }
    MAX-ACCESS 	read-write
    STATUS 	current
    DESCRIPTION 	"Clear the status log (write only)."

    ::= { logstat 1 }


logActive       OBJECT-TYPE
    SYNTAX 	INTEGER {
        off(0),
        on(1)
    }
    MAX-ACCESS 	read-write
    STATUS 	current
    DESCRIPTION 	"Enable/disable logging of alarms."

    ::= { logstat 2 }

-- logstat 3

logPage         OBJECT-TYPE
    SYNTAX 	INTEGER {
        current(0),
        first(1),
        last(2),
        prev(3),
        next(4)
    }
    MAX-ACCESS 	read-write
    STATUS 	current
    DESCRIPTION 	"Go to the specified page of the log (write only"

    ::= { logPageEntry 1 }


eventLogStorageMode OBJECT-TYPE
    SYNTAX 	INTEGER {
        logForResolution(1),
        logForDuration(2)
    }
    MAX-ACCESS 	read-write
    STATUS 	current
    DESCRIPTION 	"Event Log Storage Mode - Log for resolution/ Log for duration"

    ::= { logPageEntry 2 }


dolbyStatusProgNum OBJECT-TYPE
    SYNTAX 	INTEGER {
        prog1(1),
        prog2(2),
        prog3(3),
        prog4(4),
        prog5(5),
        prog6(6),
        prog7(7),
        prog8(8)
    }
    MAX-ACCESS 	read-write
    STATUS 	current
    DESCRIPTION 	"Dolby status page program selection"

    ::= { logPageEntry 3 }


eventLogSourceFilter OBJECT-TYPE
    SYNTAX 	INTEGER {
        all(0),
        currchan(1),
        currsrc(2),
        chan1(3)
    }
    MAX-ACCESS 	read-write
    STATUS 	current
    DESCRIPTION 	"Dolby status page program selection"

    ::= { logPageEntry 4 }


logPageTable    OBJECT-TYPE
    SYNTAX 	SEQUENCE OF LogPageEntry
    MAX-ACCESS 	not-accessible
    STATUS 	current
    DESCRIPTION 	"Table for status log viewer"

    ::= { logstat 4 }


logPageEntry    OBJECT-TYPE
    SYNTAX 	LogPageEntry
    MAX-ACCESS 	not-accessible
    STATUS 	current
    DESCRIPTION 	"A row in the logPage table "
    INDEX { currTile }

    ::= { logPageTable 1 }


LogPageEntry ::= SEQUENCE {
    logPage 	INTEGER,
    eventLogStorageMode 	INTEGER,
    dolbyStatusProgNum 	INTEGER,
    eventLogSourceFilter 	INTEGER 
}
-- 
-- audio Group
-- Audio display variables

audAuxDisplay   OBJECT-TYPE
    SYNTAX 	INTEGER {
        off(0),
        phaseDisplay(1),
        surroundDisplay(2),
        loudDisplay(3)
    }
    MAX-ACCESS 	read-write
    STATUS 	current
    DESCRIPTION 	" Enable/disable audio phase display."

    ::= { audEntry 1 }


audPhaseStyle   OBJECT-TYPE
    SYNTAX 	INTEGER {
        sound-stage(0),
        xy(1)
    }
    MAX-ACCESS 	read-write
    STATUS 	current
    DESCRIPTION 	" Audio phase orientation: Sound Stage Lissajous or X-Y Lissajous"

    ::= { audEntry 2 }


audPhasePair    OBJECT-TYPE
    SYNTAX 	INTEGER {
        custom(-1),
        pair1-2(0),
        pair3-4(1),
        pair5-6(2),
        pair7-8(3),
        pair9-10(4)
    }
    MAX-ACCESS 	read-write
    STATUS 	current
    DESCRIPTION 	"Audio channel pair to monitor in phase display."

    ::= { audEntry 3 }


audInput        OBJECT-TYPE
    SYNTAX 	INTEGER {
        analogA(1),
        analogB(2),
        aesA(3),
        aesB(4),
        embedded(5),
        follows-video(6),
        dolby1(7),
        dolby2(8),
        dolby3(9),
        dolby4(10),
        emb-16ch(11),
        emb-1to8(12),
        emb-9to16(13),
        testSignal(14)
    }
    MAX-ACCESS 	read-write
    STATUS 	current
    DESCRIPTION 	"Current audio input source."

    ::= { audEntry 4 }


audCustomPhaseA OBJECT-TYPE
    SYNTAX 	INTEGER {
        channel1(1),
        channel2(2),
        channel3(3),
        channel4(4),
        channel5(5),
        channel6(6),
        channel7(7),
        channel8(8),
        channel9(9),
        channel10(10)
    }
    MAX-ACCESS 	read-write
    STATUS 	current
    DESCRIPTION 	"Phase channel A for custom phase pair selection."

    ::= { audEntry 5 }


audCustomPhaseB OBJECT-TYPE
    SYNTAX 	INTEGER {
        channel1(1),
        channel2(2),
        channel3(3),
        channel4(4),
        channel5(5),
        channel6(6),
        channel7(7),
        channel8(8),
        channel9(9),
        channel10(10)
    }
    MAX-ACCESS 	read-write
    STATUS 	current
    DESCRIPTION 	"Phase channel B for custom phase pair selection."

    ::= { audEntry 6 }


audDolbyEPgm    OBJECT-TYPE
    SYNTAX 	INTEGER {
        prog1(1),
        prog2(2),
        prog3(3),
        prog4(4),
        prog5(5),
        prog6(6),
        prog7(7),
        prog8(8)
    }
    MAX-ACCESS 	read-write
    STATUS 	current
    DESCRIPTION 	"Dolby E program that the Surround Display is derived.This OID is active only if the current audio source is Dolby E "

    ::= { audEntry 9 }


loudnessAvg     OBJECT-TYPE
    SYNTAX 	INTEGER {
        short(0),
        long(1)
    }
    MAX-ACCESS 	read-write
    STATUS 	current
    DESCRIPTION 	"Selects the duration over which the loudness count is averaged."

    ::= { audEntry 10 }


loudnessBar     OBJECT-TYPE
    SYNTAX 	INTEGER {
        off(0),
        program(1),
        oneAndtwo(3),
        threeAndfour(4),
        fiveAndsix(5),
        sevenAndeight(6),
        nineAndten(7)
    }
    MAX-ACCESS 	read-write
    STATUS 	current
    DESCRIPTION 	"Enable/Disable Audio Loudness Bar on Audio Tile"

    ::= { audEntry 11 }


audTable        OBJECT-TYPE
    SYNTAX 	SEQUENCE OF AudEntry
    MAX-ACCESS 	not-accessible
    STATUS 	current
    DESCRIPTION 	"Table for audio mode"

    ::= { audio 1 }


audEntry        OBJECT-TYPE
    SYNTAX 	AudEntry
    MAX-ACCESS 	not-accessible
    STATUS 	current
    DESCRIPTION 	"A row in the audio table "
    INDEX { currTile }

    ::= { audTable 1 }


AudEntry ::= SEQUENCE {
    audAuxDisplay 	INTEGER,
    audPhaseStyle 	INTEGER,
    audPhasePair 	INTEGER,
    audInput 	INTEGER,
    audCustomPhaseA 	INTEGER,
    audCustomPhaseB 	INTEGER,
    audDolbyEPgm 	INTEGER,
    loudnessAvg 	INTEGER,
    loudnessBar 	INTEGER 
}
-- 
-- audioIo group
-- Audio input/output variables.

audAESportBout  OBJECT-TYPE
    SYNTAX 	INTEGER {
        off(0),
        on(1)
    }
    MAX-ACCESS 	read-write
    STATUS 	current
    DESCRIPTION 	"Set AES port B output active when embedded audio is the active audio source."

    ::= { audioIo 1 }


audAna-A-Format OBJECT-TYPE
    SYNTAX 	INTEGER {
        pairs(0),
        surround(1),
        pairsLabels(2)
    }
    MAX-ACCESS 	read-write
    STATUS 	current
    DESCRIPTION 	"Meter format for analog input A."

    ::= { audioIo 2 }


audAna-B-Format OBJECT-TYPE
    SYNTAX 	INTEGER {
        pairs(0),
        surround(1),
        pairsLabels(2)
    }
    MAX-ACCESS 	read-write
    STATUS 	current
    DESCRIPTION 	"Meter format for analog input B."

    ::= { audioIo 3 }


audAES-A-Format OBJECT-TYPE
    SYNTAX 	INTEGER {
        pairs(0),
        surround(1),
        pairsLabels(2)
    }
    MAX-ACCESS 	read-write
    STATUS 	current
    DESCRIPTION 	"Meter format for AES input A."

    ::= { audioIo 4 }


audAES-B-Format OBJECT-TYPE
    SYNTAX 	INTEGER {
        pairs(0),
        surround(1),
        pairsLabels(2)
    }
    MAX-ACCESS 	read-write
    STATUS 	current
    DESCRIPTION 	"Meter format for AES input B."

    ::= { audioIo 5 }


audEmbed-A-Format OBJECT-TYPE
    SYNTAX 	INTEGER {
        pairs(0),
        surround(1),
        pairsLabels(2)
    }
    MAX-ACCESS 	read-write
    STATUS 	current
    DESCRIPTION 	"Meter format for embedded input from SDI input A."

    ::= { audioIo 6 }


audEmbed-B-Format OBJECT-TYPE
    SYNTAX 	INTEGER {
        pairs(0),
        surround(1),
        pairsLabels(2)
    }
    MAX-ACCESS 	read-write
    STATUS 	current
    DESCRIPTION 	"Meter format for embedded input from SDI input B."

    ::= { audioIo 7 }


levelMeters     OBJECT-TYPE
    SYNTAX 	INTEGER {
        barPair1(0),
        barPair2(1),
        barPair3(2),
        barPair4(3)
    }
    MAX-ACCESS 	not-accessible
    STATUS 	current
    DESCRIPTION 	"Level meter pair number.  This variable is an index for audBarInTableThe audio bar pairs also correspond to the following surround channels:barPair1 = L & R ,barPair2 = Ls & Rs ,barPair3 = C & Lfe ,barPair4 = Lo & Ro "

    ::= { audioIo 8 }


audAES-A-BarInput OBJECT-TYPE
    SYNTAX 	INTEGER {
        none(0),
        pair1(1),
        pair2(2),
        pair3(3),
        pair4(4)
    }
    MAX-ACCESS 	read-write
    STATUS 	current
    DESCRIPTION 	"AES input assignment for each pair of level meters.  Refer to thedescription of levelMeters for mapping of surround channels tolevel meter pairs.  An AES stream may be assigned to more than onemeter pair or a meter pair may be disabled by selecting 'none'."

    ::= { audBarInEntry 1 }


audAES-B-BarInput OBJECT-TYPE
    SYNTAX 	INTEGER {
        none(0),
        pair1(1),
        pair2(2),
        pair3(3),
        pair4(4)
    }
    MAX-ACCESS 	read-write
    STATUS 	current
    DESCRIPTION 	"AES input assignment for each pair of level meters.  Refer to thedescription of levelMeters for mapping of surround channels tolevel meter pairs.  An AES stream may be assigned to more than onemeter pair or a meter pair may be disabled by selecting 'none'."

    ::= { audBarInEntry 2 }


audEmbed-A-BarInput OBJECT-TYPE
    SYNTAX 	INTEGER {
        none(0),
        pair1(1),
        pair2(2),
        pair3(3),
        pair4(4),
        pair5(5),
        pair6(6),
        pair7(7),
        pair8(8)
    }
    MAX-ACCESS 	read-write
    STATUS 	current
    DESCRIPTION 	"Embedded input assignment for each pair of level meters.Refer to the description of levelMeters for mapping ofsurround channels to level meter pairs.  An Embedded stream may be assigned to more than one meter pair or a meter pairmay be disabled by selecting 'none'."

    ::= { audBarInEntry 3 }


audEmbed-B-BarInput OBJECT-TYPE
    SYNTAX 	INTEGER {
        none(0),
        pair1(1),
        pair2(2),
        pair3(3),
        pair4(4),
        pair5(5),
        pair6(6),
        pair7(7),
        pair8(8)
    }
    MAX-ACCESS 	read-write
    STATUS 	current
    DESCRIPTION 	"Embedded input assignment for each pair of level meters.Refer to the description of levelMeters for mapping ofsurround channels to level meter pairs.  An Embedded stream may be assigned to more than one meter pair or a meter pairmay be disabled by selecting 'none'."

    ::= { audBarInEntry 4 }


audEmbedDualLinkBarInput OBJECT-TYPE
    SYNTAX 	INTEGER {
        none(0),
        link-a-pair1(1),
        link-a-pair2(2),
        link-a-pair3(3),
        link-a-pair4(4),
        link-a-pair5(5),
        link-a-pair6(6),
        link-a-pair7(7),
        link-a-pair8(8),
        link-b-pair1(9),
        link-b-pair2(10),
        link-b-pair3(11),
        link-b-pair4(12),
        link-b-pair5(13),
        link-b-pair6(14),
        link-b-pair7(15),
        link-b-pair8(16)
    }
    MAX-ACCESS 	read-write
    STATUS 	current
    DESCRIPTION 	"Embedded dual link input assignment for each pair of level meters.Refer to the description of levelMeters for mapping ofsurround channels to level meter pairs.  An Embedded dual link stream may be assigned to more than one meter pair or a meter pair may be disabled by selecting 'none'."

    ::= { audBarInEntry 5 }


dualAudioBarInput OBJECT-TYPE
    SYNTAX 	INTEGER {
        none(0),
        a1-pair1(1),
        a1-pair2(2),
        a1-pair3(3),
        a1-pair4(4),
        a1-pair5(5),
        a1-pair6(6),
        a1-pair7(7),
        a1-pair8(8),
        a2-pair1(9),
        a2-pair2(10),
        a2-pair3(11),
        a2-pair4(12),
        a2-pair5(13),
        a2-pair6(14),
        a2-pair7(15),
        a2-pair8(16)
    }
    MAX-ACCESS 	read-write
    STATUS 	current
    DESCRIPTION 	"Dual audio input assignment for each pair of level meters. Refer to the description of levelMeters for mapping of surround channels to level meter pairs. The possible range of dual audio pairs depends on the current dual audio inputs selection and allocation of bars to the two audio inputs. A dual audio pair may be assigned to more than one meter pairor a meter pair may be disabled by selecting 'none'."

    ::= { audBarInEntry 6 }


audHdmi-A-BarInput OBJECT-TYPE
    SYNTAX 	INTEGER {
        none(0),
        pair1(1),
        pair2(2),
        pair3(3),
        pair4(4)
    }
    MAX-ACCESS 	read-write
    STATUS 	current
    DESCRIPTION 	"HDMI input assignment for each pair of level meters.Refer to the description of levelMeters for mapping ofsurround channels to level meter pairs.  An HDMI stream may be assigned to more than one meter pair or a meter pairmay be disabled by selecting 'none'."

    ::= { audBarInEntry 7 }


audHdmi-B-BarInput OBJECT-TYPE
    SYNTAX 	INTEGER {
        none(0),
        pair1(1),
        pair2(2),
        pair3(3),
        pair4(4)
    }
    MAX-ACCESS 	read-write
    STATUS 	current
    DESCRIPTION 	"HDMI input assignment for each pair of level meters.Refer to the description of levelMeters for mapping ofsurround channels to level meter pairs.  An HDMI stream may be assigned to more than one meter pair or a meter pairmay be disabled by selecting 'none'."

    ::= { audBarInEntry 8 }


audBarInTable   OBJECT-TYPE
    SYNTAX 	SEQUENCE OF AudBarInEntry
    MAX-ACCESS 	not-accessible
    STATUS 	current
    DESCRIPTION 	"Table for bar to audio source input map"

    ::= { audioIo 9 }


audBarInEntry   OBJECT-TYPE
    SYNTAX 	AudBarInEntry
    MAX-ACCESS 	not-accessible
    STATUS 	current
    DESCRIPTION 	"A row in the audBarInTable "
    INDEX { levelMeters }

    ::= { audBarInTable 1 }


AudBarInEntry ::= SEQUENCE {
    audAES-A-BarInput 	INTEGER,
    audAES-B-BarInput 	INTEGER,
    audEmbed-A-BarInput 	INTEGER,
    audEmbed-B-BarInput 	INTEGER,
    audEmbedDualLinkBarInput 	INTEGER,
    dualAudioBarInput 	INTEGER,
    audHdmi-A-BarInput 	INTEGER,
    audHdmi-B-BarInput 	INTEGER 
}

analogLevelMeters OBJECT-TYPE
    SYNTAX 	INTEGER {
        barPair1(0),
        barPair2(1),
        barPair3(2)
    }
    MAX-ACCESS 	not-accessible
    STATUS 	current
    DESCRIPTION 	"Level meter pair number for Analog.  This variable is used as anindex for analogBarInTable. The audio bar pairs also correspondto the following surround channels:barPair1 = L & R ,barPair2 = Ls & Rs ,barPair3 = C & Lfe "

    ::= { audioIo 10 }


audAna-A-BarInput OBJECT-TYPE
    SYNTAX 	INTEGER {
        none(0),
        pair1(1),
        pair2(2),
        pair3(3)
    }
    MAX-ACCESS 	read-write
    STATUS 	current
    DESCRIPTION 	"Audio input assignment for each pair of level meters.  Refer to thedescription of analogLevelMeters for mapping of surround channels. Each analog audio pair corresponds to the following analog inputs:pair1 = inputs 1 & 2 ,pair2 = inputs 3 & 4 ,pair3 = inputs 5 & 6 "

    ::= { analogBarInEntry 1 }


audAna-B-BarInput OBJECT-TYPE
    SYNTAX 	INTEGER {
        none(0),
        pair1(1),
        pair2(2),
        pair3(3)
    }
    MAX-ACCESS 	read-write
    STATUS 	current
    DESCRIPTION 	"Audio input assignment for each pair of level meters.  Refer to thedescription of analogLevelMeters for mapping of surround channels. Each analog audio pair corresponds to the following analog inputs:pair1 = inputs 1 & 2 ,pair2 = inputs 3 & 4 ,pair3 = inputs 5 & 6 "

    ::= { analogBarInEntry 2 }


analogBarInTable OBJECT-TYPE
    SYNTAX 	SEQUENCE OF AnalogBarInEntry
    MAX-ACCESS 	not-accessible
    STATUS 	current
    DESCRIPTION 	"Table for bar to audio Analog source input map"

    ::= { audioIo 11 }


analogBarInEntry OBJECT-TYPE
    SYNTAX 	AnalogBarInEntry
    MAX-ACCESS 	not-accessible
    STATUS 	current
    DESCRIPTION 	"A row in the analogBarInTable "
    INDEX { analogLevelMeters }

    ::= { analogBarInTable 1 }


AnalogBarInEntry ::= SEQUENCE {
    audAna-A-BarInput 	INTEGER,
    audAna-B-BarInput 	INTEGER 
}

analogOutputs   OBJECT-TYPE
    SYNTAX 	INTEGER {
        output1(0),
        output2(1),
        output3(2),
        output4(3)
    }
    MAX-ACCESS 	not-accessible
    STATUS 	current
    DESCRIPTION 	"Analog output number.  This is used as index in audBarOutTableEach output represents a pair of analog outputs."

    ::= { audioIo 12 }


audAES-A-BarOutput OBJECT-TYPE
    SYNTAX 	INTEGER {
        phasePair(-1),
        none(0),
        pair1(1),
        pair2(2),
        pair3(3),
        pair4(4)
    }
    MAX-ACCESS 	read-write
    STATUS 	current
    DESCRIPTION 	"Analog output mapping from AES A level meters.  Routes the audioinput assigned to a meter to a pair of analog outputs.  This outputmapping is effective when the audInput configuration selects AES A"

    ::= { audBarOutEntry 1 }


audAES-B-BarOutput OBJECT-TYPE
    SYNTAX 	INTEGER {
        phasePair(-1),
        none(0),
        pair1(1),
        pair2(2),
        pair3(3),
        pair4(4)
    }
    MAX-ACCESS 	read-write
    STATUS 	current
    DESCRIPTION 	"Analog output mapping from AES B level meters.  Routes the audioinput assigned to a meter to a pair of analog outputs.  This outputmapping is effective when the audInput configuration selects AES B"

    ::= { audBarOutEntry 2 }


audAna-A-BarOutput OBJECT-TYPE
    SYNTAX 	INTEGER {
        phasePair(-1),
        none(0),
        pair1(1),
        pair2(2),
        pair3(3)
    }
    MAX-ACCESS 	read-write
    STATUS 	current
    DESCRIPTION 	"Analog output mapping from Analog A level meters.  Routes the audioinput assigned to a meter to a pair of analog outputs.  This outputmapping is effective when the audInput configuration selects Analog A"

    ::= { audBarOutEntry 3 }


audAna-B-BarOutput OBJECT-TYPE
    SYNTAX 	INTEGER {
        phasePair(-1),
        none(0),
        pair1(1),
        pair2(2),
        pair3(3)
    }
    MAX-ACCESS 	read-write
    STATUS 	current
    DESCRIPTION 	"Analog output mapping from Analog B level meters.  Routes the audioinput assigned to a meter to a pair of analog outputs.  This outputmapping is effective when the audInput configuration selectsAnalog B"

    ::= { audBarOutEntry 4 }


audEmbed-A-BarOutput OBJECT-TYPE
    SYNTAX 	INTEGER {
        phasePair(-1),
        none(0),
        pair1(1),
        pair2(2),
        pair3(3),
        pair4(4)
    }
    MAX-ACCESS 	read-write
    STATUS 	current
    DESCRIPTION 	"Analog output mapping from Embedded A level meters.Routes the audio input assigned to a meter to a pair ofanalog outputs.  This output mapping is effective when theaudInput configuration selects Embedded A"

    ::= { audBarOutEntry 5 }


audEmbed-B-BarOutput OBJECT-TYPE
    SYNTAX 	INTEGER {
        phasePair(-1),
        none(0),
        pair1(1),
        pair2(2),
        pair3(3),
        pair4(4)
    }
    MAX-ACCESS 	read-write
    STATUS 	current
    DESCRIPTION 	"Analog output mapping from Embedded B level meters.Routes the audio input assigned to a meter to a pair ofanalog outputs.  This output mapping is effective when theaudInput configuration selects Embedded B"

    ::= { audBarOutEntry 6 }


audDolby-1-BarOutput OBJECT-TYPE
    SYNTAX 	INTEGER {
        phasePair(-1),
        none(0),
        pair1(1),
        pair2(2),
        pair3(3),
        pair4(4),
        pair5(5)
    }
    MAX-ACCESS 	read-write
    STATUS 	current
    DESCRIPTION 	"Analog output mapping from Dolby 1 level meters.  Routes the audioinput assigned to a meter to a pair of analog outputs.  This outputmapping is effective when the audInput configuration selects Dolby-1 audio input "

    ::= { audBarOutEntry 7 }


audDolby-2-BarOutput OBJECT-TYPE
    SYNTAX 	INTEGER {
        phasePair(-1),
        none(0),
        pair1(1),
        pair2(2),
        pair3(3),
        pair4(4),
        pair5(5)
    }
    MAX-ACCESS 	read-write
    STATUS 	current
    DESCRIPTION 	"Analog output mapping from Dolby 2 level meters.  Routes the audioinput assigned to a meter to a pair of analog outputs.  This outputmapping is effective when the audInput configuration selects Dolby-2 audio input "

    ::= { audBarOutEntry 8 }


audDolby-3-BarOutput OBJECT-TYPE
    SYNTAX 	INTEGER {
        phasePair(-1),
        none(0),
        pair1(1),
        pair2(2),
        pair3(3),
        pair4(4),
        pair5(5)
    }
    MAX-ACCESS 	read-write
    STATUS 	current
    DESCRIPTION 	"Analog output mapping from Dolby 3 level meters.  Routes the audioinput assigned to a meter to a pair of analog outputs.  This outputmapping is effective when the audInput configuration selects Dolby-3 audio input "

    ::= { audBarOutEntry 9 }


audDolby-4-BarOutput OBJECT-TYPE
    SYNTAX 	INTEGER {
        phasePair(-1),
        none(0),
        pair1(1),
        pair2(2),
        pair3(3),
        pair4(4),
        pair5(5)
    }
    MAX-ACCESS 	read-write
    STATUS 	current
    DESCRIPTION 	"Analog output mapping from Dolby 4 level meters.  Routes the audioinput assigned to a meter to a pair of analog outputs.  This outputmapping is effective when the audInput configuration selects Dolby-4 audio input "

    ::= { audBarOutEntry 10 }


audEmbedDualLinkBarOutput OBJECT-TYPE
    SYNTAX 	INTEGER {
        undecoded(-10),
        none(0),
        pair1(1),
        pair2(2),
        pair3(3),
        pair4(4)
    }
    MAX-ACCESS 	read-write
    STATUS 	current
    DESCRIPTION 	"Analog output mapping from embedded dual link level meters.  Routes the audioinput assigned to a meter to a pair of analog outputs.  This outputmapping is effective when the audInput configuration selects embedded dual link audio "

    ::= { audBarOutEntry 11 }


dualAudioBarOutput OBJECT-TYPE
    SYNTAX 	INTEGER {
        phase-pair(-1),
        none(0),
        pair1(1),
        pair2(2),
        pair3(3),
        pair4(4)
    }
    MAX-ACCESS 	read-write
    STATUS 	current
    DESCRIPTION 	"Analog output mapping from dual audio level meters.  Routes the audioinput assigned to a meter to a pair of analog outputs.  This outputmapping is effective when the audInput configuration selects dual audio display "

    ::= { audBarOutEntry 12 }


audBarOutTable  OBJECT-TYPE
    SYNTAX 	SEQUENCE OF AudBarOutEntry
    MAX-ACCESS 	not-accessible
    STATUS 	current
    DESCRIPTION 	"Table for audio bar to output port mappings.  The table routes theaudio input source for each selected level meter to an analog output."

    ::= { audioIo 13 }


audBarOutEntry  OBJECT-TYPE
    SYNTAX 	AudBarOutEntry
    MAX-ACCESS 	not-accessible
    STATUS 	current
    DESCRIPTION 	"A row in the audBarOutTable."
    INDEX { analogOutputs }

    ::= { audBarOutTable 1 }


AudBarOutEntry ::= SEQUENCE {
    audAES-A-BarOutput 	INTEGER,
    audAES-B-BarOutput 	INTEGER,
    audAna-A-BarOutput 	INTEGER,
    audAna-B-BarOutput 	INTEGER,
    audEmbed-A-BarOutput 	INTEGER,
    audEmbed-B-BarOutput 	INTEGER,
    audDolby-1-BarOutput 	INTEGER,
    audDolby-2-BarOutput 	INTEGER,
    audDolby-3-BarOutput 	INTEGER,
    audDolby-4-BarOutput 	INTEGER,
    audEmbedDualLinkBarOutput 	INTEGER,
    dualAudioBarOutput 	INTEGER 
}

audVidMap-1A    OBJECT-TYPE
    SYNTAX 	INTEGER {
        none(0),
        aesA(1),
        aesB(2),
        analogA(3),
        analogB(4),
        embedded(5),
        dolby1(7),
        dolby2(8),
        dolby3(9),
        dolby4(10),
        embedded-16Ch(11)
    }
    MAX-ACCESS 	read-write
    STATUS 	current
    DESCRIPTION 	"Video to audio source mapping for video input 1A"

    ::= { audioIo 14 }


audVidMap-1B    OBJECT-TYPE
    SYNTAX 	INTEGER {
        none(0),
        aesA(1),
        aesB(2),
        analogA(3),
        analogB(4),
        embedded(5),
        dolby1(7),
        dolby2(8),
        dolby3(9),
        dolby4(10),
        embedded-16Ch(11)
    }
    MAX-ACCESS 	read-write
    STATUS 	current
    DESCRIPTION 	"Video to audio source mapping for video input 1B"

    ::= { audioIo 15 }


audVidMap-2A    OBJECT-TYPE
    SYNTAX 	INTEGER {
        none(0),
        aesA(1),
        aesB(2),
        analogA(3),
        analogB(4),
        embedded(5),
        dolby1(7),
        dolby2(8),
        dolby3(9),
        dolby4(10),
        embedded-16Ch(11)
    }
    MAX-ACCESS 	read-write
    STATUS 	current
    DESCRIPTION 	"Video to audio source mapping for video input 2A"

    ::= { audioIo 16 }


audVidMap-2B    OBJECT-TYPE
    SYNTAX 	INTEGER {
        none(0),
        aesA(1),
        aesB(2),
        analogA(3),
        analogB(4),
        embedded(5),
        dolby1(7),
        dolby2(8),
        dolby3(9),
        dolby4(10),
        embedded-16Ch(11)
    }
    MAX-ACCESS 	read-write
    STATUS 	current
    DESCRIPTION 	"Video to audio source mapping for video input 2B"

    ::= { audioIo 17 }


audOutLvl       OBJECT-TYPE
    SYNTAX 	DisplayString
    MAX-ACCESS 	read-write
    STATUS 	current
    DESCRIPTION 	"Analog audio output attenuation in dB."

    ::= { audioIo 18 }


audAES-A-ActvChannels OBJECT-TYPE
    SYNTAX 	DisplayString
    MAX-ACCESS 	read-write
    STATUS 	current
    DESCRIPTION 	"Active channel selections for AES A."

    ::= { audioIo 19 }


audAES-B-ActvChannels OBJECT-TYPE
    SYNTAX 	DisplayString
    MAX-ACCESS 	read-write
    STATUS 	current
    DESCRIPTION 	"Active channel selections for AES B."

    ::= { audioIo 20 }


audAna-A-ActvChannels OBJECT-TYPE
    SYNTAX 	DisplayString
    MAX-ACCESS 	read-write
    STATUS 	current
    DESCRIPTION 	"Active channel selections for Analog A."

    ::= { audioIo 21 }


audAna-B-ActvChannels OBJECT-TYPE
    SYNTAX 	DisplayString
    MAX-ACCESS 	read-write
    STATUS 	current
    DESCRIPTION 	"Active channel selections for Analog B."

    ::= { audioIo 22 }


audEmbed-A-ActvChannels OBJECT-TYPE
    SYNTAX 	DisplayString
    MAX-ACCESS 	read-write
    STATUS 	current
    DESCRIPTION 	"Active channel selections for Embedded A."

    ::= { audioIo 23 }


audEmbed-B-ActvChannels OBJECT-TYPE
    SYNTAX 	DisplayString
    MAX-ACCESS 	read-write
    STATUS 	current
    DESCRIPTION 	"Active channel selections for Embedded B."

    ::= { audioIo 24 }


audEmbInputChannelGroup OBJECT-TYPE
    SYNTAX 	INTEGER {
        none(0),
        embGroup1-2(1),
        embGroup3-4(2),
        embGroup1-3(3),
        embGroup2-4(4),
        embGroup1-4(5),
        embGroup2-3(6)
    }
    MAX-ACCESS 	read-write
    STATUS 	current
    DESCRIPTION 	"Selected embedded audio input channels group."

    ::= { audioIo 25 }


audEmbChannelsPresent OBJECT-TYPE
    SYNTAX 	DisplayString (SIZE(1..40))
    MAX-ACCESS 	read-only
    STATUS 	current
    DESCRIPTION 	"List of active embedded audio channels where P indicates presence - indicates absence and M indicates present and muted."

    ::= { audioIo 26 }


aesOutputs      OBJECT-TYPE
    SYNTAX 	INTEGER {
        output1(0),
        output2(1),
        output3(2),
        output4(3)
    }
    MAX-ACCESS 	not-accessible
    STATUS 	current
    DESCRIPTION 	"Analog output number.  This is used as index in audAESBarOutTableEach output represents a pair of AES outputs."

    ::= { audioIo 27 }


audAES-A-BarOutputAES OBJECT-TYPE
    SYNTAX 	INTEGER {
        none(0),
        pair1(1),
        pair2(2),
        pair3(3),
        pair4(4)
    }
    MAX-ACCESS 	read-write
    STATUS 	current
    DESCRIPTION 	"AES output mapping from AES A level meters.  Routes the audioinput assigned to a meter to a pair of AES outputs.  This outputmapping is effective when the audInput configuration selects AES A"

    ::= { audAESBarOutEntry 1 }


audAna-A-BarOutputAES OBJECT-TYPE
    SYNTAX 	INTEGER {
        none(0),
        pair1(1),
        pair2(2),
        pair3(3),
        pair4(4)
    }
    MAX-ACCESS 	read-write
    STATUS 	current
    DESCRIPTION 	"AES output mapping from Analog A level meters.  Routes the audioinput assigned to a meter to a pair of AES outputs.  This outputmapping is effective when the audInput configuration selects Analog A"

    ::= { audAESBarOutEntry 2 }


audAna-B-BarOutputAES OBJECT-TYPE
    SYNTAX 	INTEGER {
        none(0),
        pair1(1),
        pair2(2),
        pair3(3),
        pair4(4)
    }
    MAX-ACCESS 	read-write
    STATUS 	current
    DESCRIPTION 	"AES output mapping from Analog B level meters.  Routes the audioinput assigned to a meter to a pair of AES outputs.  This outputmapping is effective when the audInput configuration selects Analog B"

    ::= { audAESBarOutEntry 3 }


audEmbed-A-BarOutputAES OBJECT-TYPE
    SYNTAX 	INTEGER {
        none(0),
        pair1(1),
        pair2(2),
        pair3(3),
        pair4(4)
    }
    MAX-ACCESS 	read-write
    STATUS 	current
    DESCRIPTION 	"AES output mapping from Embedded A level meters.  Routes the audioinput assigned to a meter to a pair of AES outputs.  This outputmapping is effective when the audInput configuration selects Embedded Audio input from SDI A"

    ::= { audAESBarOutEntry 4 }


audEmbed-B-BarOutputAES OBJECT-TYPE
    SYNTAX 	INTEGER {
        none(0),
        pair1(1),
        pair2(2),
        pair3(3),
        pair4(4)
    }
    MAX-ACCESS 	read-write
    STATUS 	current
    DESCRIPTION 	"AES output mapping from Embedded B level meters.  Routes the audioinput assigned to a meter to a pair of AES outputs.  This outputmapping is effective when the audInput configuration selects Embedded Audio input from SDI B"

    ::= { audAESBarOutEntry 5 }


audDolby-1-BarOutputAES OBJECT-TYPE
    SYNTAX 	INTEGER {
        undecoded(-10),
        none(0),
        pair1(1),
        pair2(2),
        pair3(3),
        pair4(4),
        pair5(5)
    }
    MAX-ACCESS 	read-write
    STATUS 	current
    DESCRIPTION 	"AES output mapping from Dolby-1 level meters.  Routes the audioinput assigned to a meter to a pair of AES outputs.  This outputmapping is effective when the audInput configuration selects input from Dolby-1"

    ::= { audAESBarOutEntry 6 }


audDolby-2-BarOutputAES OBJECT-TYPE
    SYNTAX 	INTEGER {
        undecoded(-10),
        none(0),
        pair1(1),
        pair2(2),
        pair3(3),
        pair4(4),
        pair5(5)
    }
    MAX-ACCESS 	read-write
    STATUS 	current
    DESCRIPTION 	"AES output mapping from Dolby-2 level meters.  Routes the audioinput assigned to a meter to a pair of AES outputs.  This outputmapping is effective when the audInput configuration selects input from Dolby-2"

    ::= { audAESBarOutEntry 7 }


audDolby-3-BarOutputAES OBJECT-TYPE
    SYNTAX 	INTEGER {
        undecoded(-10),
        none(0),
        pair1(1),
        pair2(2),
        pair3(3),
        pair4(4),
        pair5(5)
    }
    MAX-ACCESS 	read-write
    STATUS 	current
    DESCRIPTION 	"AES output mapping from Dolby-3 level meters.  Routes the audioinput assigned to a meter to a pair of AES outputs.  This outputmapping is effective when the audInput configuration selects input from Dolby-3"

    ::= { audAESBarOutEntry 8 }


audDolby-4-BarOutputAES OBJECT-TYPE
    SYNTAX 	INTEGER {
        undecoded(-10),
        none(0),
        pair1(1),
        pair2(2),
        pair3(3),
        pair4(4),
        pair5(5)
    }
    MAX-ACCESS 	read-write
    STATUS 	current
    DESCRIPTION 	"AES output mapping from Dolby-4 level meters.  Routes the audioinput assigned to a meter to a pair of AES outputs.  This outputmapping is effective when the audInput configuration selects input from Dolby-4"

    ::= { audAESBarOutEntry 9 }


audEmbedDualLinkBarOutputAES OBJECT-TYPE
    SYNTAX 	INTEGER {
        undecoded(-10),
        none(0),
        pair1(1),
        pair2(2),
        pair3(3),
        pair4(4)
    }
    MAX-ACCESS 	read-write
    STATUS 	current
    DESCRIPTION 	"AES output mapping from embedded dual link level meters. Routes the audio input assigned to a meter to a pair of AES outputs.  This output mapping is effective when the audInput configuration selects input from embedded dual link"

    ::= { audAESBarOutEntry 10 }


dualAudioBarOutputAES OBJECT-TYPE
    SYNTAX 	INTEGER {
        undecoded(-10),
        none(0),
        pair1(1),
        pair2(2),
        pair3(3),
        pair4(4)
    }
    MAX-ACCESS 	read-write
    STATUS 	current
    DESCRIPTION 	"AES output mapping from dual audio level meters. Routes the audio input assigned to a meter to a pair of AES outputs.  This output mapping is effective when the audInput configuration select dual audio display"

    ::= { audAESBarOutEntry 11 }


audAESBarOutTable OBJECT-TYPE
    SYNTAX 	SEQUENCE OF AudAESBarOutEntry
    MAX-ACCESS 	not-accessible
    STATUS 	current
    DESCRIPTION 	"Table for audio bar to output port mappings.  The table routes theaudio input source for each selected level meter to an AES output."

    ::= { audioIo 28 }


audAESBarOutEntry OBJECT-TYPE
    SYNTAX 	AudAESBarOutEntry
    MAX-ACCESS 	not-accessible
    STATUS 	current
    DESCRIPTION 	"A row in the audAESBarOutTable."
    INDEX { aesOutputs }

    ::= { audAESBarOutTable 1 }


AudAESBarOutEntry ::= SEQUENCE {
    audAES-A-BarOutputAES 	INTEGER,
    audAna-A-BarOutputAES 	INTEGER,
    audAna-B-BarOutputAES 	INTEGER,
    audEmbed-A-BarOutputAES 	INTEGER,
    audEmbed-B-BarOutputAES 	INTEGER,
    audDolby-1-BarOutputAES 	INTEGER,
    audDolby-2-BarOutputAES 	INTEGER,
    audDolby-3-BarOutputAES 	INTEGER,
    audDolby-4-BarOutputAES 	INTEGER,
    audEmbedDualLinkBarOutputAES 	INTEGER,
    dualAudioBarOutputAES 	INTEGER 
}

audAES-A-Reference OBJECT-TYPE
    SYNTAX 	INTEGER {
        off(0),
        aesA1-2(1),
        aesA3-4(2),
        aesA5-6(3),
        aesA7-8(4)
    }
    MAX-ACCESS 	read-write
    STATUS 	current
    DESCRIPTION 	"AES Reference for AES-A input."

    ::= { audioIo 29 }


audAES-B-Reference OBJECT-TYPE
    SYNTAX 	INTEGER {
        off(0),
        aesB1-2(1),
        aesB3-4(2),
        aesB5-6(3),
        aesB7-8(4)
    }
    MAX-ACCESS 	read-write
    STATUS 	current
    DESCRIPTION 	"AES Reference for AES-B input."

    ::= { audioIo 30 }


dolbyInputs     OBJECT-TYPE
    SYNTAX 	INTEGER {
        dolby1(0),
        dolby2(1),
        dolby3(2),
        dolby4(3)
    }
    MAX-ACCESS 	not-accessible
    STATUS 	current
    DESCRIPTION 	"Dolby Inputs.  This is used as index in dolbyInputTable."

    ::= { audioIo 31 }


audDolbySource  OBJECT-TYPE
    SYNTAX 	INTEGER {
        aesA1-2(11),
        aesA3-4(12),
        aesA5-6(13),
        aesA7-8(14),
        aesB1-2(21),
        aesB3-4(22),
        aesB5-6(23),
        aesB7-8(24),
        emb1-2(101),
        emb3-4(102),
        emb5-6(103),
        emb7-8(104),
        emb9-10(105),
        emb11-12(106),
        emb13-14(107),
        emb15-16(108)
    }
    MAX-ACCESS 	read-write
    STATUS 	current
    DESCRIPTION 	"Dolby Input Source Selection. Selects which channel go to the dolby decoder"

    ::= { dolbyInputCfgEntry 1 }


dolbyExpectedFormat OBJECT-TYPE
    SYNTAX 	INTEGER {
        anyDolby(0),
        dolbyD(1),
        dolbyE(2),
        dolbyDPlus(3)
    }
    MAX-ACCESS 	read-write
    STATUS 	current
    DESCRIPTION 	"Dolby Format alarm. Causes an alarm to be thrown if the dolby format is not as expected"

    ::= { dolbyInputCfgEntry 2 }


dolbyEPgmMask   OBJECT-TYPE
    SYNTAX 	BITS {
        prog1(0),
        prog2(1),
        prog3(2),
        prog4(3),
        prog5(4),
        prog6(5),
        prog7(6),
        prog8(7)
    }
    MAX-ACCESS 	read-write
    STATUS 	current
    DESCRIPTION 	"Dolby Program Mask for allow alarm. Each bit in the octet selects Dolby E pgm channel for alarm "

    ::= { dolbyInputCfgEntry 3 }


dolbyChanMask   OBJECT-TYPE
    SYNTAX 	BITS {
        l(0),
        r(1),
        c(2),
        lfe(3),
        ls(4),
        rs(5),
        lb(6),
        rb(7),
        lo(8),
        ro(9),
        lt(10),
        rt(11),
        s(12),
        m(13),
        le(14),
        re(15)
    }
    MAX-ACCESS 	read-write
    STATUS 	current
    DESCRIPTION 	"Dolby channel Mask for allow alarm. Defines active channels with a Dolby D audio stream or a Dolby E program. Enabling a bit for a channel enables alarms for all instances of a channel type in all active programs"

    ::= { dolbyInputCfgEntry 4 }


dolbyDAesChannel OBJECT-TYPE
    SYNTAX 	INTEGER {
        chan1(0),
        chan2(1)
    }
    MAX-ACCESS 	read-write
    STATUS 	current
    DESCRIPTION 	"Dolby D(AC3) Input Configuration, AES Channel. Selects 16-bit Dolbydigial bit stream from either the left or the right channel of an AES audio stream in which up to two different Dolby D bitstreams  have been encoded in each channel"

    ::= { dolbyInputCfgEntry 5 }


dolbyDAesStream OBJECT-TYPE
    SYNTAX 	INTEGER {
        auto(0),
        stream1(1),
        stream2(2),
        stream3(3),
        stream4(4),
        stream5(5),
        stream6(6),
        stream7(7)
    }
    MAX-ACCESS 	read-write
    STATUS 	current
    DESCRIPTION 	"Dolby D(AC3) Input Configuration ,Stream Select. Selects the data stream number of one of up to 8 Dolby D bitstreams that have been time multiplexed within an AES data stream using the burst packet forma defined by SMPTE 337M"

    ::= { dolbyInputCfgEntry 6 }


dolbyEDownmixPgm OBJECT-TYPE
    SYNTAX 	INTEGER {
        prog1(1),
        prog2(2),
        prog3(3),
        prog4(4),
        prog5(5),
        prog6(6),
        prog7(7),
        prog8(8)
    }
    MAX-ACCESS 	read-write
    STATUS 	current
    DESCRIPTION 	"Dolby E Downmix program. selects which Dolby E program is downmixedand output on the aux output of the CAT552"

    ::= { dolbyInputCfgEntry 7 }


aesRefEnable    OBJECT-TYPE
    SYNTAX 	INTEGER {
        off(0),
        on(1)
    }
    MAX-ACCESS 	read-write
    STATUS 	current
    DESCRIPTION 	"AES Reference Enable, if Dolby Source is set to an AES inputsets the rasterizer to detect if the AES Input is unlocked from theAES reference. If this is set the AES Frame Sync Alarm maybe thrown. The default setting is off."

    ::= { dolbyInputCfgEntry 8 }


dolbyInputTable OBJECT-TYPE
    SYNTAX 	SEQUENCE OF DolbyInputCfgEntry
    MAX-ACCESS 	not-accessible
    STATUS 	current
    DESCRIPTION 	"Table for dolby input sources configuration."

    ::= { audioIo 32 }


dolbyInputCfgEntry OBJECT-TYPE
    SYNTAX 	DolbyInputCfgEntry
    MAX-ACCESS 	not-accessible
    STATUS 	current
    DESCRIPTION 	"A row in the dolbyInputTable."
    INDEX { dolbyInputs }

    ::= { dolbyInputTable 1 }


DolbyInputCfgEntry ::= SEQUENCE {
    audDolbySource 	INTEGER,
    dolbyExpectedFormat 	INTEGER,
    dolbyEPgmMask 	BITS,
    dolbyChanMask 	BITS,
    dolbyDAesChannel 	INTEGER,
    dolbyDAesStream 	INTEGER,
    dolbyEDownmixPgm 	INTEGER,
    aesRefEnable 	INTEGER 
}

dolbyDListeningMode OBJECT-TYPE
    SYNTAX 	INTEGER {
        full(0),
        ex(1),
        stereo-3(2),
        phantom(3),
        stereo(4),
        mono(5),
        proLogicFull(6),
        proLogic3Stereo(7),
        proLogicPhantom(8)
    }
    MAX-ACCESS 	read-write
    STATUS 	current
    DESCRIPTION 	"Dolby D(AC3) Setup, Listening mode. Selects listening mode.for the specified Dolby input "

    ::= { audioIo 33 }


dolbyDDialnormDrc OBJECT-TYPE
    SYNTAX 	INTEGER {
        off(0),
        dialnormOnly(1),
        lineModeDrc(2),
        rfModeDrc(3)
    }
    MAX-ACCESS 	read-write
    STATUS 	current
    DESCRIPTION 	"Dolby D (AC3) Dialnorm and dynamic range. Selects Dynamic RangeCompression (DRC) mode for Dolby Digital audio. Dialnorm setting is enabled for all DRC modes. dialnormOnly adjust audio levels fordialog but disables compression. lineModeDrc and rfModeDrc enableaudio level compression and dialnorm "

    ::= { audioIo 34 }


dolbyDDownmixDynRng OBJECT-TYPE
    SYNTAX 	INTEGER {
        line(0),
        rf(1)
    }
    MAX-ACCESS 	read-write
    STATUS 	current
    DESCRIPTION 	"Dolby D (AC3) Downmix dynamic range. Used to select RF or Line.dynamic range compression on downmix "

    ::= { audioIo 35 }


dolbyEDialnorm  OBJECT-TYPE
    SYNTAX 	INTEGER {
        off(0),
        on(1)
    }
    MAX-ACCESS 	read-write
    STATUS 	current
    DESCRIPTION 	"Dolby E Setup, Dialnorm. If enabled this setting applies dialog.normalization to the audio bars,analog and digital outputs "

    ::= { audioIo 36 }


dolbyEPulldownDecoding OBJECT-TYPE
    SYNTAX 	INTEGER {
        off(0),
        on(1)
    }
    MAX-ACCESS 	read-write
    STATUS 	current
    DESCRIPTION 	"Dolby E Setup Pulldown decoding. Enables pulldown decoding method.for Dolby E signal.Used when tape recorders operate at lower  than 30fps."

    ::= { audioIo 37 }


dolbyDownmixMode OBJECT-TYPE
    SYNTAX 	INTEGER {
        none(0),
        lt-Rt(1),
        lo-Ro(2),
        mono(3)
    }
    MAX-ACCESS 	read-write
    STATUS 	current
    DESCRIPTION 	"Selects a downmix program configuration for the currently selected.Dolby D or Dolby E audio program. The option none(0) disables the DolbyDownmix and removes the audio level meters from the audio display."

    ::= { audioIo 38 }


audEmbedPhaseAlignA OBJECT-TYPE
    SYNTAX 	INTEGER {
        off(0),
        on(1)
    }
    MAX-ACCESS 	read-write
    STATUS 	current
    DESCRIPTION 	"SDI Channel A Embedded group phase align, ensures that Audio Channelsin different groups are co-sited (aligned) "

    ::= { audioIo 39 }


audEmbedPhaseAlignB OBJECT-TYPE
    SYNTAX 	INTEGER {
        off(0),
        on(1)
    }
    MAX-ACCESS 	read-write
    STATUS 	current
    DESCRIPTION 	"SDI Channel B Embedded group phase align, ensures that Audio Channelsin different groups are co-sited (aligned) "

    ::= { audioIo 40 }


dolbyLoudnessChans OBJECT-TYPE
    SYNTAX 	BITS {
        l(0),
        r(1),
        c(2),
        lfe(3),
        ls(4),
        rs(5),
        lb(6),
        rb(7),
        s(8),
        m(9),
        le(10),
        re(11)
    }
    MAX-ACCESS 	read-write
    STATUS 	current
    DESCRIPTION 	"Defines active channels for inclusion into the Dolby Program Loudness calculation"

    ::= { audioIo 41 }


audEmbedDualLinkFormat OBJECT-TYPE
    SYNTAX 	INTEGER {
        pairs(0),
        surround(1),
        pairsLabels(2)
    }
    MAX-ACCESS 	read-write
    STATUS 	current
    DESCRIPTION 	"Meter format for embedded dual link audio."

    ::= { audioIo 42 }


audEmbedDualLinkActvChannels OBJECT-TYPE
    SYNTAX 	DisplayString
    MAX-ACCESS 	read-write
    STATUS 	current
    DESCRIPTION 	"Active channel selections for Embedded Dual Link audio."

    ::= { audioIo 43 }


audEmbedDualLinkPhaseAlign OBJECT-TYPE
    SYNTAX 	INTEGER {
        off(0),
        on(1)
    }
    MAX-ACCESS 	read-write
    STATUS 	current
    DESCRIPTION 	"Embedded Dual Link group phase align, ensures that Audio Channels in different groups are co-sited (aligned) "

    ::= { audioIo 44 }


dualAudioFormat OBJECT-TYPE
    SYNTAX 	INTEGER {
        pairs(0),
        surround(1),
        pairsLabels(2)
    }
    MAX-ACCESS 	read-write
    STATUS 	current
    DESCRIPTION 	"Meter format for dual audio dispaly."

    ::= { audioIo 45 }


dualAudioAllocateBars OBJECT-TYPE
    SYNTAX 	INTEGER {
        bars-8-0(0),
        bars-6-2(1),
        bars-4-4(2),
        bars-2-6(3),
        bars-0-8(4)
    }
    MAX-ACCESS 	read-write
    STATUS 	current
    DESCRIPTION 	"Allocate bars for dual audio display."

    ::= { audioIo 46 }


dualAudioInput  OBJECT-TYPE
    SYNTAX 	BITS {
        a1-aesA(0),
        a1-aesB(1),
        a1-embedded(2),
        a1-analogA(3),
        a1-analogB(4),
        a1-dolby1(5),
        a1-dolby2(6),
        a1-dolby3(7),
        a1-dolby4(8),
        a2-aesA(9),
        a2-aesB(10),
        a2-embedded(11),
        a2-analogA(12),
        a2-analogB(13),
        a2-dolby1(14),
        a2-dolby2(15),
        a2-dolby3(16),
        a2-dolby4(17)
    }
    MAX-ACCESS 	read-write
    STATUS 	current
    DESCRIPTION 	"Dual audio input selections."

    ::= { audioIo 47 }


dualAudioActvChannels OBJECT-TYPE
    SYNTAX 	DisplayString
    MAX-ACCESS 	read-write
    STATUS 	current
    DESCRIPTION 	"Active channel selections for Dual audio display."

    ::= { audioIo 48 }


dolbyEGuardLimitModeSD OBJECT-TYPE
    SYNTAX 	INTEGER {
        disabled(0),
        rdd6(1),
        custom(2),
        dolbyValid(3),
        dolbyIdeal(4)
    }
    MAX-ACCESS 	read-write
    STATUS 	current
    DESCRIPTION 	"Mode for determining Dolby E guardband (SD/Composite"

    ::= { audioIo 49 }


dolbyEGuardLimitMinSD OBJECT-TYPE
    SYNTAX 	INTEGER (8..30)
    MAX-ACCESS 	read-write
    STATUS 	current
    DESCRIPTION 	"First line of custom Dolby E guardband (SD/Composite"

    ::= { audioIo 50 }


dolbyEGuardLimitMaxSD OBJECT-TYPE
    SYNTAX 	INTEGER (8..30)
    MAX-ACCESS 	read-write
    STATUS 	current
    DESCRIPTION 	"Last line of custom Dolby E guardband (SD/Composite"

    ::= { audioIo 51 }


dolbyEGuardLimitModeHD OBJECT-TYPE
    SYNTAX 	INTEGER {
        disabled(0),
        rdd6(1),
        custom(2),
        dolbyValid(3),
        dolbyIdeal(4)
    }
    MAX-ACCESS 	read-write
    STATUS 	current
    DESCRIPTION 	"Mode for determining Dolby E guardband (HD/Dual Link/3Gb"

    ::= { audioIo 52 }


dolbyEGuardLimitMinHD OBJECT-TYPE
    SYNTAX 	INTEGER (9..70)
    MAX-ACCESS 	read-write
    STATUS 	current
    DESCRIPTION 	"First line of custom Dolby E guardband (HD/Dual Link/3Gb"

    ::= { audioIo 53 }


dolbyEGuardLimitMaxHD OBJECT-TYPE
    SYNTAX 	INTEGER (9..70)
    MAX-ACCESS 	read-write
    STATUS 	current
    DESCRIPTION 	"Last line of custom Dolby E guardband (HD/Dual Link/3Gb"

    ::= { audioIo 54 }


loudnessConfigPreset OBJECT-TYPE
    SYNTAX 	INTEGER {
        none(0),
        iec61672(1),
        atscA85-2011(2),
        ebuR128LU9(3),
        ebuR128LU18(4),
        aribTrB32(5),
        freeTvOP59(6),
        brazilOrd354(7),
        atscA85-2013(8)
    }
    MAX-ACCESS 	read-write
    STATUS 	current
    DESCRIPTION 	"Loudness Display Configuration Preset (write-only)"

    ::= { audioIo 55 }


loudnessMomentIntegTime OBJECT-TYPE
    SYNTAX 	INTEGER (125..400)
    MAX-ACCESS 	read-write
    STATUS 	current
    DESCRIPTION 	"Audio Loudness Momentary Integration Time. Use values 125 and 400 only."

    ::= { audioIo 56 }


loudnessAveIntegTime OBJECT-TYPE
    SYNTAX 	INTEGER (0..60)
    MAX-ACCESS 	read-write
    STATUS 	current
    DESCRIPTION 	"Audio Loudness Average Integration Time"

    ::= { audioIo 57 }


loudnessChanWeight OBJECT-TYPE
    SYNTAX 	INTEGER {
        custom(0),
        all(1),
        excludeLfe(2),
        ituRbs1770(3)
    }
    MAX-ACCESS 	read-write
    STATUS 	current
    DESCRIPTION 	"Audio Loudness Channel Weighting Settings"

    ::= { audioIo 58 }


loudnessTargetType OBJECT-TYPE
    SYNTAX 	INTEGER {
        manual(0),
        dialnorm(1)
    }
    MAX-ACCESS 	not-accessible
    STATUS 	current
    DESCRIPTION 	"Not used"

    ::= { audioIo 59 }


loudnessGatingType OBJECT-TYPE
    SYNTAX 	INTEGER {
        disabled(0),
        safetyOnly(1),
        relative(3)
    }
    MAX-ACCESS 	read-write
    STATUS 	current
    DESCRIPTION 	"Audio Loudness Measure Gating Type.  Controls whether or not gating is applied to calculation of infinite loudness.  In pregate or fixed loudness, a fixed threshold is used; in relative gating, both a fixed (pregate) and a relative threshold are used."

    ::= { audioIo 60 }


loudnessTargetLvl OBJECT-TYPE
    SYNTAX 	INTEGER (-37..6)
    MAX-ACCESS 	read-write
    STATUS 	current
    DESCRIPTION 	"Audio Loudness Measure loudness target in LKFS"

    ::= { audioIo 61 }


loudTargetPlus  OBJECT-TYPE
    SYNTAX 	INTEGER (0..10)
    MAX-ACCESS 	read-write
    STATUS 	current
    DESCRIPTION 	"Acceptable upper deviation (in LU) from the target level"

    ::= { audioIo 62 }


loudnessTargetMinus OBJECT-TYPE
    SYNTAX 	INTEGER (0..10)
    MAX-ACCESS 	read-write
    STATUS 	current
    DESCRIPTION 	"Acceptable lower deviation (in LU) from the target level"

    ::= { audioIo 63 }


loudnessPreGateLvl OBJECT-TYPE
    SYNTAX 	INTEGER (-99..-40)
    MAX-ACCESS 	not-accessible
    STATUS 	current
    DESCRIPTION 	"Not used"

    ::= { audioIo 64 }


loudnessGatingFixThresh OBJECT-TYPE
    SYNTAX 	INTEGER (-99..-40)
    MAX-ACCESS 	read-write
    STATUS 	current
    DESCRIPTION 	"Saftey Gate Level."

    ::= { audioIo 65 }


loudnessGatingRelThresh OBJECT-TYPE
    SYNTAX 	INTEGER (-30..0)
    MAX-ACCESS 	read-write
    STATUS 	current
    DESCRIPTION 	"Relative loudness level (in loudness units) used to gate infinite loudness measurement; when difference between momentary loudness measurement and ungated infinite average exceeds this threshold, and relative gating ie enabled, measurements are excluded from infinite loudness calculations.  Use a relative gate of -8LU to comply with EBU R/128."

    ::= { audioIo 66 }


loudnessDBUtoDBFS OBJECT-TYPE
    SYNTAX 	INTEGER (-24..-12)
    MAX-ACCESS 	read-write
    STATUS 	current
    DESCRIPTION 	"Analog to Digital Units for Loudness"

    ::= { audioIo 67 }


setZeroLUMark   OBJECT-TYPE
    SYNTAX 	INTEGER {
        fullScale(0),
        targetLoud(1)
    }
    MAX-ACCESS 	read-write
    STATUS 	current
    DESCRIPTION 	"Set 0 LU Mark to Full Scale or Target Loud."

    ::= { audioIo 68 }


loudnessWeightFilter OBJECT-TYPE
    SYNTAX 	INTEGER {
        linear(0),
        a-weighted(1),
        bs1770(2)
    }
    MAX-ACCESS 	read-write
    STATUS 	current
    DESCRIPTION 	"Select Loudness Filter Weighting for Surround Sound Display."

    ::= { audioIo 69 }


loudnessGateIntegrationTime OBJECT-TYPE
    SYNTAX 	INTEGER (0..2000)
    MAX-ACCESS 	read-write
    STATUS 	current
    DESCRIPTION 	"Gating block integration time (in milliseconds)."

    ::= { audioIo 70 }


loudnessGateOverlapTime OBJECT-TYPE
    SYNTAX 	INTEGER (0..2000)
    MAX-ACCESS 	read-write
    STATUS 	current
    DESCRIPTION 	"Gating block integration time (in milliseconds)."

    ::= { audioIo 71 }


loudnessProgramDetect OBJECT-TYPE
    SYNTAX 	INTEGER {
        off(0),
        on(1)
    }
    MAX-ACCESS 	read-write
    STATUS 	current
    DESCRIPTION 	"Controls program edge detection for loudness measurement."

    ::= { audioIo 72 }


audioProgram    OBJECT-TYPE
    SYNTAX 	INTEGER {
        ch1pgmSel(0),
        ch1pgm1(1),
        ch1pgm2(2),
        ch1pgm3(3),
        ch1pgm4(4),
        ch1pgm5(5),
        ch1pgm6(6),
        ch1pgm7(7),
        ch1pgm8(8),
        ch2pgmSel(9),
        ch2pgm1(10),
        ch2pgm2(11),
        ch2pgm3(12),
        ch2pgm4(13),
        ch2pgm5(14),
        ch2pgm6(15),
        ch2pgm7(16),
        ch2pgm8(17)
    }
    MAX-ACCESS 	not-accessible
    STATUS 	current
    DESCRIPTION 	"Audio mon chan/pgm.  This is used as an index in tables"

    ::= { audioIo 73 }


momentaryLoudness OBJECT-TYPE
    SYNTAX 	AudioLevel
    MAX-ACCESS 	read-only
    STATUS 	current
    DESCRIPTION 	"Momentary (M) program loudness"

    ::= { audLoudnessEntry 1 }


shortTermLoudness OBJECT-TYPE
    SYNTAX 	AudioLevel
    MAX-ACCESS 	read-only
    STATUS 	current
    DESCRIPTION 	"Short-term (S) program loudness"

    ::= { audLoudnessEntry 2 }


infiniteLoudness OBJECT-TYPE
    SYNTAX 	AudioLevel
    MAX-ACCESS 	read-only
    STATUS 	current
    DESCRIPTION 	"Infinite (I) program loudness"

    ::= { audLoudnessEntry 3 }


dialogLevel     OBJECT-TYPE
    SYNTAX 	AudioLevel
    MAX-ACCESS 	read-only
    STATUS 	current
    DESCRIPTION 	"Dolby dialog level metadata"

    ::= { audLoudnessEntry 4 }


loudRange       OBJECT-TYPE
    SYNTAX 	AudioLevel
    MAX-ACCESS 	read-only
    STATUS 	current
    DESCRIPTION 	"Loudness range per EBU Tech. 3342"

    ::= { audLoudnessEntry 5 }


truePeak        OBJECT-TYPE
    SYNTAX 	AudioLevel
    MAX-ACCESS 	read-only
    STATUS 	current
    DESCRIPTION 	"Program true peak level"

    ::= { audLoudnessEntry 6 }


audLoudnessTable OBJECT-TYPE
    SYNTAX 	SEQUENCE OF AudLoudnessEntry
    MAX-ACCESS 	not-accessible
    STATUS 	current
    DESCRIPTION 	"Table for audio program loudness values"

    ::= { audioIo 74 }


audLoudnessEntry OBJECT-TYPE
    SYNTAX 	AudLoudnessEntry
    MAX-ACCESS 	not-accessible
    STATUS 	current
    DESCRIPTION 	"A row in the audLoudnessTable "
    INDEX { audioProgram }

    ::= { audLoudnessTable 1 }


AudLoudnessEntry ::= SEQUENCE {
    momentaryLoudness 	AudioLevel,
    shortTermLoudness 	AudioLevel,
    infiniteLoudness 	AudioLevel,
    dialogLevel 	AudioLevel,
    loudRange 	AudioLevel,
    truePeak 	AudioLevel 
}

audioMonChannel OBJECT-TYPE
    SYNTAX 	INTEGER {
        chan1(0),
        chan2(1)
    }
    MAX-ACCESS 	read-write
    STATUS 	current
    DESCRIPTION 	"Selects monitoring channel for SIM mode on WFM/WVR5200"

    ::= { audioIo 75 }


audProgCfgAesA  OBJECT-TYPE
    SYNTAX 	INTEGER {
        mono(0),
        stereo(1),
        lcrs(2),
        quad(3),
        lcrlfe(4),
        surrStereo(5),
        surrMono(6),
        cfg7-1(7),
        cfg2-5-1(8)
    }
    MAX-ACCESS 	read-write
    STATUS 	current
    DESCRIPTION 	"Customize the labels associated with AES A surround configuration"

    ::= { audioIo 76 }


audProgCfgAesB  OBJECT-TYPE
    SYNTAX 	INTEGER {
        mono(0),
        stereo(1),
        lcrs(2),
        quad(3),
        lcrlfe(4),
        surrStereo(5),
        surrMono(6),
        cfg7-1(7),
        cfg2-5-1(8)
    }
    MAX-ACCESS 	read-write
    STATUS 	current
    DESCRIPTION 	"Customize the labels associated with AES B surround configuration"

    ::= { audioIo 77 }


audProgCfgEmbA  OBJECT-TYPE
    SYNTAX 	INTEGER {
        mono(0),
        stereo(1),
        lcrs(2),
        quad(3),
        lcrlfe(4),
        surrStereo(5),
        surrMono(6),
        cfg7-1(7),
        cfg2-5-1(8)
    }
    MAX-ACCESS 	read-write
    STATUS 	current
    DESCRIPTION 	"Customize the labels associated with embedded A surround configuration"

    ::= { audioIo 78 }


audProgCfgEmbB  OBJECT-TYPE
    SYNTAX 	INTEGER {
        mono(0),
        stereo(1),
        lcrs(2),
        quad(3),
        lcrlfe(4),
        surrStereo(5),
        surrMono(6),
        cfg7-1(7),
        cfg2-5-1(8)
    }
    MAX-ACCESS 	read-write
    STATUS 	current
    DESCRIPTION 	"Customize the labels associated with embedded B surround configuration"

    ::= { audioIo 79 }


audProgCfgEmbDual OBJECT-TYPE
    SYNTAX 	INTEGER {
        mono(0),
        stereo(1),
        lcrs(2),
        quad(3),
        lcrlfe(4),
        surrStereo(5),
        surrMono(6),
        cfg7-1(7),
        cfg2-5-1(8)
    }
    MAX-ACCESS 	read-write
    STATUS 	current
    DESCRIPTION 	"Customize the labels associated with dula link surround configuration"

    ::= { audioIo 80 }


audSurMapAesA   OBJECT-TYPE
    SYNTAX 	INTEGER {
        smpte320(0),
        uk(1)
    }
    MAX-ACCESS 	read-write
    STATUS 	current
    DESCRIPTION 	"Audio surround mapping for AES A"

    ::= { audioIo 81 }


audSurMapAesB   OBJECT-TYPE
    SYNTAX 	INTEGER {
        smpte320(0),
        uk(1)
    }
    MAX-ACCESS 	read-write
    STATUS 	current
    DESCRIPTION 	"Audio surround mapping AES B"

    ::= { audioIo 82 }


audSurMapEmbA   OBJECT-TYPE
    SYNTAX 	INTEGER {
        smpte320(0),
        uk(1)
    }
    MAX-ACCESS 	read-write
    STATUS 	current
    DESCRIPTION 	"Audio surround mapping embedded A"

    ::= { audioIo 83 }


audSurMapEmbB   OBJECT-TYPE
    SYNTAX 	INTEGER {
        smpte320(0),
        uk(1)
    }
    MAX-ACCESS 	read-write
    STATUS 	current
    DESCRIPTION 	"Audio surround mapping for embedded B"

    ::= { audioIo 84 }


audSurMapEmbDual OBJECT-TYPE
    SYNTAX 	INTEGER {
        smpte320(0),
        uk(1)
    }
    MAX-ACCESS 	read-write
    STATUS 	current
    DESCRIPTION 	"Audio surround mapping for dual link embedded"

    ::= { audioIo 85 }


audEmbed-Dual-Format OBJECT-TYPE
    SYNTAX 	INTEGER {
        pairs(0),
        surround(1),
        pairsLabels(2)
    }
    MAX-ACCESS 	read-write
    STATUS 	current
    DESCRIPTION 	"Meter format for dual link embedded input"

    ::= { audioIo 86 }


audProgCfgHdmiA OBJECT-TYPE
    SYNTAX 	INTEGER {
        mono(0),
        stereo(1),
        lcrs(2),
        quad(3),
        lcrlfe(4),
        surrStereo(5),
        surrMono(6),
        cfg7-1(7),
        cfg2-5-1(8),
        hdmi-3-2-1(9),
        hdmi-3-3-1(10),
        hdmi-3-4-1(11),
        hdmi-5-1-1(12),
        hdmi-5-2-1(13)
    }
    MAX-ACCESS 	read-write
    STATUS 	current
    DESCRIPTION 	"Customize the labels associated with HDMI A surround configuration"

    ::= { audioIo 87 }


audProgCfgHdmiB OBJECT-TYPE
    SYNTAX 	INTEGER {
        mono(0),
        stereo(1),
        lcrs(2),
        quad(3),
        lcrlfe(4),
        surrStereo(5),
        surrMono(6),
        cfg7-1(7),
        cfg2-5-1(8),
        hdmi-3-2-1(9),
        hdmi-3-3-1(10),
        hdmi-3-4-1(11),
        hdmi-5-1-1(12),
        hdmi-5-2-1(13)
    }
    MAX-ACCESS 	read-write
    STATUS 	current
    DESCRIPTION 	"Customize the labels associated with HDMI B surround configuration"

    ::= { audioIo 88 }


audSurMapHdmiA  OBJECT-TYPE
    SYNTAX 	INTEGER {
        lfe-c(0),
        c-lfe(1)
    }
    MAX-ACCESS 	read-write
    STATUS 	current
    DESCRIPTION 	"Audio surround mapping HDMI A"

    ::= { audioIo 89 }


audSurMapHdmiB  OBJECT-TYPE
    SYNTAX 	INTEGER {
        lfe-c(0),
        c-lfe(1)
    }
    MAX-ACCESS 	read-write
    STATUS 	current
    DESCRIPTION 	"Audio surround mapping for HDMI B"

    ::= { audioIo 90 }


audHdmi-A-Format OBJECT-TYPE
    SYNTAX 	INTEGER {
        pairs(0),
        surround(1),
        pairLabels(2),
        pairs-lr-c-lfe(3),
        pairs-lr-lfe-c(4)
    }
    MAX-ACCESS 	read-write
    STATUS 	current
    DESCRIPTION 	"Meter format for embedded input from HDMI input A."

    ::= { audioIo 91 }


audHdmi-B-Format OBJECT-TYPE
    SYNTAX 	INTEGER {
        pairs(0),
        surround(1),
        pairLabels(2),
        pairs-lr-c-lfe(3),
        pairs-lr-lfe-c(4)
    }
    MAX-ACCESS 	read-write
    STATUS 	current
    DESCRIPTION 	"Meter format for embedded input from HDMI input B."

    ::= { audioIo 92 }

-- 
-- traps.
-- traps Group.
trapPrefix      OBJECT IDENTIFIER ::= { traps 0 }


trapDestnNum    OBJECT-TYPE
    SYNTAX 	INTEGER (0..3)
    MAX-ACCESS 	not-accessible
    STATUS 	current
    DESCRIPTION 	"Trap destination number for use as an index in the trap destination table"

    ::= { traps 1 }


trapReport      OBJECT-TYPE
    SYNTAX 	INTEGER {
        off(0),
        on(1)
    }
    MAX-ACCESS 	read-write
    STATUS 	current
    DESCRIPTION 	"Enable/Disable trap reporting"

    ::= { traps 2 }


trapDestn       OBJECT-TYPE
    SYNTAX 	DisplayString
    MAX-ACCESS 	read-write
    STATUS 	current
    DESCRIPTION 	"Destination IP address for traps"

    ::= { trapDestnEntry 1 }


trapDestnTable  OBJECT-TYPE
    SYNTAX 	SEQUENCE OF TrapDestnEntry
    MAX-ACCESS 	not-accessible
    STATUS 	current
    DESCRIPTION 	"Table for trap destination addresses"

    ::= { traps 3 }


trapDestnEntry  OBJECT-TYPE
    SYNTAX 	TrapDestnEntry
    MAX-ACCESS 	not-accessible
    STATUS 	current
    DESCRIPTION 	"a row in the trap destination address table"
    INDEX { trapDestnNum }

    ::= { trapDestnTable 1 }


TrapDestnEntry ::= SEQUENCE {
    trapDestn 	DisplayString 
}

trapInfo        OBJECT-TYPE
    SYNTAX 	DisplayString
    MAX-ACCESS 	accessible-for-notify
    STATUS 	current
    DESCRIPTION 	"Additional information sent along with the trap. (not accessible for GET/SET requests)"

    ::= { traps 4 }


alarmType       OBJECT-TYPE
    SYNTAX 	INTEGER {
        alarm(0),
        alarmStart(1),
        alarmEnd(2)
    }
    MAX-ACCESS 	accessible-for-notify
    STATUS 	current
    DESCRIPTION 	"Alarm type.  An alarm is a discrete event.  Start and end events announce the start and end of a continuous alarm condition.  Discrete alarms may also be escalated to continuous alarms if the events occur too frequently.  The instrument may also send additional alarm start traps to provide updated information about the alarm state such as changes in faults detected or affected channels."

    ::= { traps 5 }


sdiSigLossTrap NOTIFICATION-TYPE
    STATUS 	current
    DESCRIPTION 	"Change in the presence of SDI Input Signal"

    ::= { trapPrefix 1 }


sdiEdhTrap NOTIFICATION-TYPE
    STATUS 	current
    DESCRIPTION 	"EDH errors"

    ::= { trapPrefix 2 }


sdiFFCrcTrap NOTIFICATION-TYPE
    STATUS 	current
    DESCRIPTION 	"EDH errors in Full Field"

    ::= { trapPrefix 3 }


sdiAPCrcTrap NOTIFICATION-TYPE
    STATUS 	current
    DESCRIPTION 	"EDH errors in Active Picture"

    ::= { trapPrefix 4 }


sdiAesChksumTrap NOTIFICATION-TYPE
    STATUS 	current
    DESCRIPTION 	"AES audio chesksum errors"

    ::= { trapPrefix 5 }


sdiAesFullTrap NOTIFICATION-TYPE
    STATUS 	deprecated
    DESCRIPTION 	"AES audio extraction buffer FULL errors"

    ::= { trapPrefix 6 }


sdiAesEmptyTrap NOTIFICATION-TYPE
    STATUS 	deprecated
    DESCRIPTION 	"AES audio extraction buffer EMPTY errors"

    ::= { trapPrefix 7 }


sdiAudioMissTrap NOTIFICATION-TYPE
    STATUS 	current
    DESCRIPTION 	"Embedded audio channel missing errors"

    ::= { trapPrefix 8 }


sdiAudioPrtyTrap NOTIFICATION-TYPE
    STATUS 	current
    DESCRIPTION 	"Embedded audio channel parity errors"

    ::= { trapPrefix 9 }


cpstSigLossTrap NOTIFICATION-TYPE
    STATUS 	current
    DESCRIPTION 	"Composite input signal missing"

    ::= { trapPrefix 10 }


refMissTrap NOTIFICATION-TYPE
    STATUS 	current
    DESCRIPTION 	"Reference input missing"

    ::= { trapPrefix 11 }


audSigLockTrap NOTIFICATION-TYPE
    STATUS 	current
    DESCRIPTION 	"Change in the presence of a signal on one or more audio input pairs"

    ::= { trapPrefix 12 }


audCrcTrap NOTIFICATION-TYPE
    STATUS 	current
    DESCRIPTION 	"CRC errors on one or more AES audio inputs"

    ::= { trapPrefix 13 }


audValidTrap NOTIFICATION-TYPE
    STATUS 	current
    DESCRIPTION 	"Incorrectly set VALID bit on one or more AES audio inputs"

    ::= { trapPrefix 14 }


audParityTrap NOTIFICATION-TYPE
    STATUS 	current
    DESCRIPTION 	"Parity errors on one or more AES audio inputs"

    ::= { trapPrefix 15 }


audSlipTrap NOTIFICATION-TYPE
    STATUS 	current
    DESCRIPTION 	"Slipped samples on one or more AES audio inputs"

    ::= { trapPrefix 16 }


audClipTrap NOTIFICATION-TYPE
    STATUS 	current
    DESCRIPTION 	"Signal clipping on one or more of the audio input channels"

    ::= { trapPrefix 17 }


audOverTrap NOTIFICATION-TYPE
    STATUS 	current
    DESCRIPTION 	"Signals are over the volume threshold for one or more of the audio input channels"

    ::= { trapPrefix 18 }


audMuteTrap NOTIFICATION-TYPE
    STATUS 	current
    DESCRIPTION 	"Digital mutes on one or more of the audio inputs channels"

    ::= { trapPrefix 19 }


audSilenceTrap NOTIFICATION-TYPE
    STATUS 	current
    DESCRIPTION 	"Extended period of silence on one or more of the audio input channels"

    ::= { trapPrefix 20 }


ltcMissingTrap NOTIFICATION-TYPE
    STATUS 	current
    DESCRIPTION 	"LTC code missing"

    ::= { trapPrefix 21 }


vitcMissingTrap NOTIFICATION-TYPE
    STATUS 	current
    DESCRIPTION 	"VITC code missing"

    ::= { trapPrefix 22 }


compUnlockedTrap NOTIFICATION-TYPE
    STATUS 	current
    DESCRIPTION 	"Composite input unlocked"

    ::= { trapPrefix 23 }


refUnlockedTrap NOTIFICATION-TYPE
    STATUS 	current
    DESCRIPTION 	"External reference unlocked"

    ::= { trapPrefix 24 }


hwFaultTrap NOTIFICATION-TYPE
    STATUS 	current
    DESCRIPTION 	"Hardware fault (fan failures, over temperatures, etc)"

    ::= { trapPrefix 25 }


sdiUnlockedTrap NOTIFICATION-TYPE
    STATUS 	current
    DESCRIPTION 	"SDI input unlocked"

    ::= { trapPrefix 26 }


ltcInvalidTrap NOTIFICATION-TYPE
    STATUS 	current
    DESCRIPTION 	"LTC code invalid"

    ::= { trapPrefix 27 }


vitcInvalidTrap NOTIFICATION-TYPE
    STATUS 	current
    DESCRIPTION 	"VITC code invalid"

    ::= { trapPrefix 28 }


gamutRgbTrap NOTIFICATION-TYPE
    STATUS 	current
    DESCRIPTION 	"RGB gamut error"

    ::= { trapPrefix 29 }


gamutCompositeTrap NOTIFICATION-TYPE
    STATUS 	current
    DESCRIPTION 	"Composite gamut error"

    ::= { trapPrefix 30 }


gamutLumaTrap NOTIFICATION-TYPE
    STATUS 	current
    DESCRIPTION 	"Luma gamut error"

    ::= { trapPrefix 31 }


refVideoTrap NOTIFICATION-TYPE
    STATUS 	current
    DESCRIPTION 	"Reference video error"

    ::= { trapPrefix 32 }


cableLengthTrap NOTIFICATION-TYPE
    STATUS 	current
    DESCRIPTION 	"Cable length error"

    ::= { trapPrefix 33 }


srcLevelTrap NOTIFICATION-TYPE
    STATUS 	current
    DESCRIPTION 	"Source level error"

    ::= { trapPrefix 34 }


ccActvTransMissing NOTIFICATION-TYPE
    STATUS 	current
    DESCRIPTION 	"Closed caption presence error"

    ::= { trapPrefix 35 }


ancPresenceTrap NOTIFICATION-TYPE
    STATUS 	current
    DESCRIPTION 	"Ancillary data presence error"

    ::= { trapPrefix 36 }


ancPlacementTrap NOTIFICATION-TYPE
    STATUS 	current
    DESCRIPTION 	"Ancillary data placement error"

    ::= { trapPrefix 37 }


sdiYAncParityTrap NOTIFICATION-TYPE
    STATUS 	current
    DESCRIPTION 	"Sdi Y Ancillary data parity error"

    ::= { trapPrefix 38 }


sdiCAncParityTrap NOTIFICATION-TYPE
    STATUS 	current
    DESCRIPTION 	"Sdi C Ancillary data parity error"

    ::= { trapPrefix 39 }


sdiCodeTrap NOTIFICATION-TYPE
    STATUS 	current
    DESCRIPTION 	"SDI code error"

    ::= { trapPrefix 40 }


sdiDataTrap NOTIFICATION-TYPE
    STATUS 	current
    DESCRIPTION 	"SDI data error"

    ::= { trapPrefix 41 }


sdiFieldTrap NOTIFICATION-TYPE
    STATUS 	current
    DESCRIPTION 	"SDI field error"

    ::= { trapPrefix 42 }


sdiLineTrap NOTIFICATION-TYPE
    STATUS 	current
    DESCRIPTION 	"SDI line error"

    ::= { trapPrefix 43 }


sdiHdLineTrap NOTIFICATION-TYPE
    STATUS 	current
    DESCRIPTION 	"SDI HD line error"

    ::= { trapPrefix 44 }


sdiNoEavTrap NOTIFICATION-TYPE
    STATUS 	current
    DESCRIPTION 	"SDI no EAV error"

    ::= { trapPrefix 45 }


sdiNoSavTrap NOTIFICATION-TYPE
    STATUS 	current
    DESCRIPTION 	"SDI no SAV error"

    ::= { trapPrefix 46 }


sdiBadCrcTrap NOTIFICATION-TYPE
    STATUS 	current
    DESCRIPTION 	"SDI bad CRC error"

    ::= { trapPrefix 47 }


sdiBadCrcYTrap NOTIFICATION-TYPE
    STATUS 	current
    DESCRIPTION 	"SDI bad CRC Y error"

    ::= { trapPrefix 48 }


sdiBadCrcCTrap NOTIFICATION-TYPE
    STATUS 	current
    DESCRIPTION 	"SDI bad CRC C error"

    ::= { trapPrefix 49 }


embAudioChecksumTrap NOTIFICATION-TYPE
    STATUS 	current
    DESCRIPTION 	"Embedded audio checksum error"

    ::= { trapPrefix 50 }


aesAudioCodeTrap NOTIFICATION-TYPE
    STATUS 	current
    DESCRIPTION 	"AES audio code error"

    ::= { trapPrefix 51 }


aesAudioAbsentTrap NOTIFICATION-TYPE
    STATUS 	current
    DESCRIPTION 	"AES audio absent error"

    ::= { trapPrefix 52 }


aesAudioFormatTrap NOTIFICATION-TYPE
    STATUS 	current
    DESCRIPTION 	"AES audio format error"

    ::= { trapPrefix 53 }


aesAudioLowConfTrap NOTIFICATION-TYPE
    STATUS 	current
    DESCRIPTION 	"AES audio low confidence error"

    ::= { trapPrefix 54 }


inputSigNotHDTrap NOTIFICATION-TYPE
    STATUS 	current
    DESCRIPTION 	"Input signal not HD"

    ::= { trapPrefix 55 }


fmtChangeTrap NOTIFICATION-TYPE
    STATUS 	current
    DESCRIPTION 	"Format change error"

    ::= { trapPrefix 56 }


videoFmtMismatchTrap NOTIFICATION-TYPE
    STATUS 	current
    DESCRIPTION 	"Input video format mismatch"

    ::= { trapPrefix 57 }


refFmtMismatchTrap NOTIFICATION-TYPE
    STATUS 	current
    DESCRIPTION 	"Ext reference format mismatch"

    ::= { trapPrefix 58 }


ancVitcInvalidTrap NOTIFICATION-TYPE
    STATUS 	current
    DESCRIPTION 	"Anc VITC invalid"

    ::= { trapPrefix 59 }


ancVitcMissingTrap NOTIFICATION-TYPE
    STATUS 	current
    DESCRIPTION 	"Anc VITC missing"

    ::= { trapPrefix 60 }


eyeAmpTrap NOTIFICATION-TYPE
    STATUS 	current
    DESCRIPTION 	"Eye pattern amplitude out of limits"

    ::= { trapPrefix 61 }


eyeRiseTrap NOTIFICATION-TYPE
    STATUS 	current
    DESCRIPTION 	"Eye rise time out of limits"

    ::= { trapPrefix 62 }


eyeFallTrap NOTIFICATION-TYPE
    STATUS 	current
    DESCRIPTION 	"Eye fall time out of limits"

    ::= { trapPrefix 63 }


eyeRiseFallDeltaTrap NOTIFICATION-TYPE
    STATUS 	current
    DESCRIPTION 	"Eye rise/fall delta error"

    ::= { trapPrefix 64 }


eyeRiseOverTrap NOTIFICATION-TYPE
    STATUS 	current
    DESCRIPTION 	"Eye rising edge overshoot out of limits"

    ::= { trapPrefix 65 }


eyeFallOverTrap NOTIFICATION-TYPE
    STATUS 	current
    DESCRIPTION 	"Eye falling edge overshoot out of limits"

    ::= { trapPrefix 66 }


jitLevelTrap NOTIFICATION-TYPE
    STATUS 	current
    DESCRIPTION 	"Jitter level amplitude out of limits"

    ::= { trapPrefix 67 }


ccChangedTrap NOTIFICATION-TYPE
    STATUS 	current
    DESCRIPTION 	"Closed caption status change notification"

    ::= { trapPrefix 68 }


ccParityCksmTrap NOTIFICATION-TYPE
    STATUS 	current
    DESCRIPTION 	"Closed caption parity/checksum error"

    ::= { trapPrefix 69 }


ccProtocolTrap NOTIFICATION-TYPE
    STATUS 	current
    DESCRIPTION 	"Closed caption protocol error"

    ::= { trapPrefix 70 }


vChipMissingTrap NOTIFICATION-TYPE
    STATUS 	current
    DESCRIPTION 	"V-Chip signal presence"

    ::= { trapPrefix 71 }


vchipChangedTrap NOTIFICATION-TYPE
    STATUS 	current
    DESCRIPTION 	"V-Chip rating change notification"

    ::= { trapPrefix 72 }


ccSvcMissingTrap NOTIFICATION-TYPE
    STATUS 	deprecated
    DESCRIPTION 	"Closed caption service presence"

    ::= { trapPrefix 73 }


ancB39PresTrap NOTIFICATION-TYPE
    STATUS 	current
    DESCRIPTION 	"anc B39 data packets presence"

    ::= { trapPrefix 74 }


sdiBadCksmYAncTrap NOTIFICATION-TYPE
    STATUS 	current
    DESCRIPTION 	"SDI bad checksum Y Anc error"

    ::= { trapPrefix 75 }


sdiBadCksmCAncTrap NOTIFICATION-TYPE
    STATUS 	current
    DESCRIPTION 	"SDI bad checksum C Anc error"

    ::= { trapPrefix 76 }


ccLine21TransMissingTrap NOTIFICATION-TYPE
    STATUS 	current
    DESCRIPTION 	"Asserted when Line21 captions are not present on the current video input"

    ::= { trapPrefix 77 }


smpte334mMissingTrap NOTIFICATION-TYPE
    STATUS 	current
    DESCRIPTION 	"Asserted when SMPTE334M Anc captions are not present on the current video input"

    ::= { trapPrefix 78 }


ccErrorTrap NOTIFICATION-TYPE
    STATUS 	current
    DESCRIPTION 	"Any parity, checksum or protocol error occurred in the CEA608 caption data"

    ::= { trapPrefix 79 }


vChipFormatTrap NOTIFICATION-TYPE
    STATUS 	current
    DESCRIPTION 	"A content advisory packet contained illegal data or was formatted incorrectly"

    ::= { trapPrefix 80 }


xdsErrorTrap NOTIFICATION-TYPE
    STATUS 	current
    DESCRIPTION 	"A checksum or protocol error occurred in an XDS packet"

    ::= { trapPrefix 81 }


cdpErrorTrap NOTIFICATION-TYPE
    STATUS 	current
    DESCRIPTION 	"An error occurred in the EIA708 Caption Data Payload. CDP is the outermost layer of EIA708."

    ::= { trapPrefix 82 }


tsidMissingTrap NOTIFICATION-TYPE
    STATUS 	current
    DESCRIPTION 	"No TSID packet has been detected for atleast ?? seconds."

    ::= { trapPrefix 83 }


tsidErrorTrap NOTIFICATION-TYPE
    STATUS 	current
    DESCRIPTION 	"TSID packet is present, but don't match the set of allowable values."

    ::= { trapPrefix 84 }


audioFrameSyncTrap NOTIFICATION-TYPE
    STATUS 	current
    DESCRIPTION 	"AES Reference and the active audio input(s)is(are)not synchronous"

    ::= { trapPrefix 85 }


audio-VideoSyncTrap NOTIFICATION-TYPE
    STATUS 	current
    DESCRIPTION 	"Audio to Video Sync Error"

    ::= { trapPrefix 86 }


dolbyFormatMismatchTrap NOTIFICATION-TYPE
    STATUS 	current
    DESCRIPTION 	"Dolby fromat is set to auto and the detected format is not Dolby Or the dolby format detected  is not the set dolby format"

    ::= { trapPrefix 87 }


dolbyVideoSyncTrap NOTIFICATION-TYPE
    STATUS 	current
    DESCRIPTION 	"Dolby Stream frame rate is not the same as the video frame rate"

    ::= { trapPrefix 88 }


audEmbedGroupSamplePhaseTrap NOTIFICATION-TYPE
    STATUS 	current
    DESCRIPTION 	"Sample phase errors between the selected embedded audio groups"

    ::= { trapPrefix 89 }


jitLevelTrap2 NOTIFICATION-TYPE
    STATUS 	current
    DESCRIPTION 	"Jitter2 Level amplitude out of limits"

    ::= { trapPrefix 90 }


cableLossTrap NOTIFICATION-TYPE
    STATUS 	current
    DESCRIPTION 	"Cable loss as measured by the cabel meter is out of limits"

    ::= { trapPrefix 91 }


eyeUnlockedTrap NOTIFICATION-TYPE
    STATUS 	current
    DESCRIPTION 	"The eye option is unlocked"

    ::= { trapPrefix 92 }


audChanLoudTrap NOTIFICATION-TYPE
    STATUS 	current
    DESCRIPTION 	"An Audio Channel is above the specified threshold"

    ::= { trapPrefix 93 }


audPgmLoudTrap NOTIFICATION-TYPE
    STATUS 	current
    DESCRIPTION 	"An Audio Program is above the specified threshold"

    ::= { trapPrefix 94 }


ancB37Trap NOTIFICATION-TYPE
    STATUS 	current
    DESCRIPTION 	"ARIB B37 data packets missing trap"

    ::= { trapPrefix 95 }


ancB35Trap NOTIFICATION-TYPE
    STATUS 	current
    DESCRIPTION 	"ARIB B35 data packets missing trap"

    ::= { trapPrefix 96 }


ancB23-1Trap NOTIFICATION-TYPE
    STATUS 	current
    DESCRIPTION 	"ARIB B23-1 data packets missing trap"

    ::= { trapPrefix 97 }


ancB23-2Trap NOTIFICATION-TYPE
    STATUS 	current
    DESCRIPTION 	"ARIB B23-2 data packets missing trap"

    ::= { trapPrefix 98 }


ancB22Trap NOTIFICATION-TYPE
    STATUS 	current
    DESCRIPTION 	"ARIB B22 data packets missing trap"

    ::= { trapPrefix 99 }


ancITU1685 NOTIFICATION-TYPE
    STATUS 	current
    DESCRIPTION 	"ITU1685 data packets missing trap"

    ::= { trapPrefix 100 }


smpte352MissingTrap NOTIFICATION-TYPE
    STATUS 	current
    DESCRIPTION 	"SMPTE352 data packets missing trap"

    ::= { trapPrefix 101 }


audCtrlTrap NOTIFICATION-TYPE
    STATUS 	current
    DESCRIPTION 	"Audio Control data packets missing trap"

    ::= { trapPrefix 102 }


dualLinkTimingErrorTrap NOTIFICATION-TYPE
    STATUS 	current
    DESCRIPTION 	"Dual link timing error trap"

    ::= { trapPrefix 103 }


dualLinkFmtMismatchTrap NOTIFICATION-TYPE
    STATUS 	current
    DESCRIPTION 	"Dual link format mismatch trap"

    ::= { trapPrefix 104 }


avDelayTrap NOTIFICATION-TYPE
    STATUS 	current
    DESCRIPTION 	"AV delay value trap"

    ::= { trapPrefix 105 }


afdMissingTrap NOTIFICATION-TYPE
    STATUS 	current
    DESCRIPTION 	"Active Format Description missing trap"

    ::= { trapPrefix 106 }


wssMissingTrap NOTIFICATION-TYPE
    STATUS 	current
    DESCRIPTION 	"Wide Screen Signalling missing trap"

    ::= { trapPrefix 107 }


viMissingTrap NOTIFICATION-TYPE
    STATUS 	current
    DESCRIPTION 	"Video Index information missing trap"

    ::= { trapPrefix 108 }


dolbyETimingTrap NOTIFICATION-TYPE
    STATUS 	current
    DESCRIPTION 	"Dolby E Video timing trap"

    ::= { trapPrefix 109 }


dolbyPaAlignTrap NOTIFICATION-TYPE
    STATUS 	current
    DESCRIPTION 	"Dolby PA alignment trap"

    ::= { trapPrefix 110 }


dolbyCrcErrorTrap NOTIFICATION-TYPE
    STATUS 	current
    DESCRIPTION 	"Dolby CRC error trap"

    ::= { trapPrefix 111 }


wstVbiMissingTrap NOTIFICATION-TYPE
    STATUS 	current
    DESCRIPTION 	"VBI WST  missing trap"

    ::= { trapPrefix 112 }


op47MissingTrap NOTIFICATION-TYPE
    STATUS 	current
    DESCRIPTION 	"OP47 Anc teletext missing trap"

    ::= { trapPrefix 113 }


op47ProtocolErrorTrap NOTIFICATION-TYPE
    STATUS 	current
    DESCRIPTION 	"OP47 protocol error trap"

    ::= { trapPrefix 114 }


eia708ProtocolErrorTrap NOTIFICATION-TYPE
    STATUS 	current
    DESCRIPTION 	"CEA708 protocol error trap"

    ::= { trapPrefix 115 }


wstProtocolErrorTrap NOTIFICATION-TYPE
    STATUS 	current
    DESCRIPTION 	"WST protocol error trap"

    ::= { trapPrefix 116 }


cc608SvcMissingTrap NOTIFICATION-TYPE
    STATUS 	current
    DESCRIPTION 	"CEA608 services missing"

    ::= { trapPrefix 117 }


cc708SvcMissingTrap NOTIFICATION-TYPE
    STATUS 	current
    DESCRIPTION 	"CEA708 services missing"

    ::= { trapPrefix 118 }


ccWstPageMissingTrap NOTIFICATION-TYPE
    STATUS 	current
    DESCRIPTION 	"Teletext pages missing"

    ::= { trapPrefix 119 }


rp207ErrorTrap NOTIFICATION-TYPE
    STATUS 	current
    DESCRIPTION 	"RP207 error"

    ::= { trapPrefix 120 }


copyrightStatusTrap NOTIFICATION-TYPE
    STATUS 	current
    DESCRIPTION 	"Copyright status error"

    ::= { trapPrefix 121 }


copyrightStatusChangeTrap NOTIFICATION-TYPE
    STATUS 	current
    DESCRIPTION 	"Copyright status change"

    ::= { trapPrefix 122 }


blackDetectTrap NOTIFICATION-TYPE
    STATUS 	current
    DESCRIPTION 	"Black detect error"

    ::= { trapPrefix 123 }


frozenFrameTrap NOTIFICATION-TYPE
    STATUS 	current
    DESCRIPTION 	"Frozen frame error"

    ::= { trapPrefix 124 }


ancLtcInvalidTrap NOTIFICATION-TYPE
    STATUS 	current
    DESCRIPTION 	"Anc LTC invalid"

    ::= { trapPrefix 125 }


ancLtcMissingTrap NOTIFICATION-TYPE
    STATUS 	current
    DESCRIPTION 	"Anc LTC missing"

    ::= { trapPrefix 126 }


sourceIdAlarmTrap NOTIFICATION-TYPE
    STATUS 	current
    DESCRIPTION 	"Source ID error"

    ::= { trapPrefix 127 }


sourceIdChangedTrap NOTIFICATION-TYPE
    STATUS 	current
    DESCRIPTION 	"Source ID changed"

    ::= { trapPrefix 128 }


audPgmQuietTrap NOTIFICATION-TYPE
    STATUS 	current
    DESCRIPTION 	"An Audio Program is below the specified threshold"

    ::= { trapPrefix 129 }


audSessLoudTrap NOTIFICATION-TYPE
    STATUS 	current
    DESCRIPTION 	"Audio Program loudness is above the target range"

    ::= { trapPrefix 130 }


audSessQuietTrap NOTIFICATION-TYPE
    STATUS 	current
    DESCRIPTION 	"Audio Program loudness is below the target range"

    ::= { trapPrefix 131 }


audDialnormTrap NOTIFICATION-TYPE
    STATUS 	current
    DESCRIPTION 	"Dialnorm value differs from target loudness"

    ::= { trapPrefix 132 }


aesFrameErrorTrap NOTIFICATION-TYPE
    STATUS 	current
    DESCRIPTION 	"AES Z Preamble Error"

    ::= { trapPrefix 133 }


audPhaseErrorTrap NOTIFICATION-TYPE
    STATUS 	current
    DESCRIPTION 	"Audio Phase Error"

    ::= { trapPrefix 134 }


refGenLockUnlockedTrap NOTIFICATION-TYPE
    STATUS 	current
    DESCRIPTION 	"Reference Genlock Unlocked "

    ::= { trapPrefix 135 }


hdmiAcpPacketMissingTrap NOTIFICATION-TYPE
    STATUS 	current
    DESCRIPTION 	"HDMI Audio Content Protection Packet Missing"

    ::= { trapPrefix 136 }


hdmiIsrcPacketMissingTrap NOTIFICATION-TYPE
    STATUS 	current
    DESCRIPTION 	"HDMI ISRC Packet Missing"

    ::= { trapPrefix 137 }


hdmiGamutPacketMissingTrap NOTIFICATION-TYPE
    STATUS 	current
    DESCRIPTION 	"HDMI Gamut Packet Missing"

    ::= { trapPrefix 138 }


hdmiVendorInfoMissingTrap NOTIFICATION-TYPE
    STATUS 	current
    DESCRIPTION 	"HDMI Vendor Specific InfoFrame Missing"

    ::= { trapPrefix 139 }


hdmiAviInfoMissingTrap NOTIFICATION-TYPE
    STATUS 	current
    DESCRIPTION 	"HDMI AVI InfoFrame Missing"

    ::= { trapPrefix 140 }


hdmiSourceProdInfoMissingTrap NOTIFICATION-TYPE
    STATUS 	current
    DESCRIPTION 	"HDMI Source Product Descriptor InfoFrame Missing"

    ::= { trapPrefix 141 }


hdmiAudioInfoMissingTrap NOTIFICATION-TYPE
    STATUS 	current
    DESCRIPTION 	"HDMI Audio InfoFrame Missing"

    ::= { trapPrefix 142 }


hdmiMpegSourceInfoMissingTrap NOTIFICATION-TYPE
    STATUS 	current
    DESCRIPTION 	"HDMI MPEG Source InfoFrame Missing"

    ::= { trapPrefix 143 }


ancB37ProtocolTrap NOTIFICATION-TYPE
    STATUS 	current
    DESCRIPTION 	"ARIB B37 data protocol error trap"

    ::= { trapPrefix 144 }


ancAribCcMissingTrap NOTIFICATION-TYPE
    STATUS 	current
    DESCRIPTION 	"ARIB CC missing trap"

    ::= { trapPrefix 145 }


ancAribCcProtocolTrap NOTIFICATION-TYPE
    STATUS 	current
    DESCRIPTION 	"ARIB CC protocol error trap"

    ::= { trapPrefix 146 }


ancS2031MissingTrap NOTIFICATION-TYPE
    STATUS 	current
    DESCRIPTION 	"S2031 (DVB/SCTE) missing trap"

    ::= { trapPrefix 147 }


ancS2031ProtocolTrap NOTIFICATION-TYPE
    STATUS 	current
    DESCRIPTION 	"S2031 (DVB/SCTE) protocol error trap"

    ::= { trapPrefix 148 }

-- 
-- alarm group.
-- Alarm configuration variables.

alarmMute       OBJECT-TYPE
    SYNTAX 	INTEGER {
        off(0),
        on(1)
    }
    MAX-ACCESS 	read-write
    STATUS 	current
    DESCRIPTION 	"Suspend sending alarms to Beep, SNMP, Ground Closure and Pop-up"

    ::= { alarm 1 }


alarmEnable     OBJECT-TYPE
    SYNTAX 	INTEGER {
        off(0),
        on(1)
    }
    MAX-ACCESS 	read-write
    STATUS 	current
    DESCRIPTION 	"Enable/Disable all alarms without changing individual settings"

    ::= { alarm 2 }


sdiSigLoss      OBJECT-TYPE
    SYNTAX 	DisplayString
    MAX-ACCESS 	read-write
    STATUS 	current
    DESCRIPTION 	"Alarm notification configuration for SDI input signal loss. Select one or more of the following: ui icon log beep snmp gc"

    ::= { alarm 3 }


sdiBadEdh       OBJECT-TYPE
    SYNTAX 	DisplayString
    MAX-ACCESS 	read-write
    STATUS 	current
    DESCRIPTION 	"Alarm notification configuration for SDI SD EDH error. Select one or more of the following: ui icon log beep snmp gc"

    ::= { alarm 4 }


gamutRgb        OBJECT-TYPE
    SYNTAX 	DisplayString
    MAX-ACCESS 	read-write
    STATUS 	current
    DESCRIPTION 	"Alarm notification configuration for RGB gamut errors. Select one or more of the following: ui icon log beep snmp gc"

    ::= { alarm 5 }


gamutComposite  OBJECT-TYPE
    SYNTAX 	DisplayString
    MAX-ACCESS 	read-write
    STATUS 	current
    DESCRIPTION 	"Alarm notification configuration for composite gamut violations. Select one or more of the following: ui icon log beep snmp gc"

    ::= { alarm 6 }


compSigLoss     OBJECT-TYPE
    SYNTAX 	DisplayString
    MAX-ACCESS 	read-write
    STATUS 	current
    DESCRIPTION 	"Alarm notification configuration for composite input signal loss. Select one or more of the following: ui icon log beep snmp gc"

    ::= { alarm 7 }


refMissing      OBJECT-TYPE
    SYNTAX 	DisplayString
    MAX-ACCESS 	read-write
    STATUS 	current
    DESCRIPTION 	"Alarm notification configuration for missing external reference signal. Select one or more of the following: ui icon log beep snmp gc"

    ::= { alarm 8 }


ltcMissing      OBJECT-TYPE
    SYNTAX 	DisplayString
    MAX-ACCESS 	read-write
    STATUS 	current
    DESCRIPTION 	"Alarm notification configuration for missing LTC timecode. Select one or more of the following: ui icon log beep snmp gc"

    ::= { alarm 9 }


vitcMissing     OBJECT-TYPE
    SYNTAX 	DisplayString
    MAX-ACCESS 	read-write
    STATUS 	current
    DESCRIPTION 	"Alarm notification configuration for missing VITC timecode. Select one or more of the following: ui icon log beep snmp gc"

    ::= { alarm 10 }


audioClip       OBJECT-TYPE
    SYNTAX 	DisplayString
    MAX-ACCESS 	read-write
    STATUS 	current
    DESCRIPTION 	"Alarm notification configuration for digital audio siganl clipping. Select one or more of the following: ui icon log beep snmp gc"

    ::= { alarm 11 }


audioMute       OBJECT-TYPE
    SYNTAX 	DisplayString
    MAX-ACCESS 	read-write
    STATUS 	current
    DESCRIPTION 	"Alarm notification configuration for digital audio mute detection. Select one or more of the following: ui icon log beep snmp gc"

    ::= { alarm 12 }


audioOver       OBJECT-TYPE
    SYNTAX 	DisplayString
    MAX-ACCESS 	read-write
    STATUS 	current
    DESCRIPTION 	"Alarm notification configuration for audio over volume threshold. Select one or more of the following: ui icon log beep snmp gc"

    ::= { alarm 13 }


audioSilence    OBJECT-TYPE
    SYNTAX 	DisplayString
    MAX-ACCESS 	read-write
    STATUS 	current
    DESCRIPTION 	"Alarm notification configuration for audio silence. Select one or more of the following: ui icon log beep snmp gc"

    ::= { alarm 14 }


audioSigLock    OBJECT-TYPE
    SYNTAX 	DisplayString
    MAX-ACCESS 	read-write
    STATUS 	current
    DESCRIPTION 	"Alarm notification configuration for loss of AES audio lock. Select one or more of the following: ui icon log beep snmp gc"

    ::= { alarm 15 }


audioCrc        OBJECT-TYPE
    SYNTAX 	DisplayString
    MAX-ACCESS 	read-write
    STATUS 	current
    DESCRIPTION 	"Alarm notification configuration for AES audio CRC errors. Select one or more of the following: ui icon log beep snmp gc"

    ::= { alarm 16 }


audioValidBit   OBJECT-TYPE
    SYNTAX 	DisplayString
    MAX-ACCESS 	read-write
    STATUS 	current
    DESCRIPTION 	"Alarm notification configuration for incorrect VALID bit in AES. Select one or more of the following: ui icon log beep snmp gc"

    ::= { alarm 17 }


audioParity     OBJECT-TYPE
    SYNTAX 	DisplayString
    MAX-ACCESS 	read-write
    STATUS 	current
    DESCRIPTION 	"Alarm notification configuration for parity error in AES stream. Select one or more of the following: ui icon log beep snmp gc"

    ::= { alarm 18 }


eAudStreamMissing OBJECT-TYPE
    SYNTAX 	DisplayString
    MAX-ACCESS 	read-write
    STATUS 	current
    DESCRIPTION 	"Alarm notification configuration for embedded audio missing. Select one or more of the following: ui icon log beep snmp gc"

    ::= { alarm 19 }


eAudStreamChksum OBJECT-TYPE
    SYNTAX 	DisplayString
    MAX-ACCESS 	read-write
    STATUS 	current
    DESCRIPTION 	"Alarm notification configuration for embedded audio checksum error . Select one or more of the following: ui icon log beep snmp gc"

    ::= { alarm 20 }


eAudStreamParity OBJECT-TYPE
    SYNTAX 	DisplayString
    MAX-ACCESS 	read-write
    STATUS 	current
    DESCRIPTION 	"Alarm notification configuration for embedded audio parity error . Select one or more of the following: ui icon log beep snmp gc"

    ::= { alarm 21 }


compUnlocked    OBJECT-TYPE
    SYNTAX 	DisplayString
    MAX-ACCESS 	read-write
    STATUS 	current
    DESCRIPTION 	"Alarm notification configuration for unlocked composite input. Select one or more of the following: ui icon log beep snmp gc"

    ::= { alarm 22 }


refUnlocked     OBJECT-TYPE
    SYNTAX 	DisplayString
    MAX-ACCESS 	read-write
    STATUS 	current
    DESCRIPTION 	"Alarm notification configuration for unlocked external reference . Select one or more of the following: ui icon log beep snmp gc"

    ::= { alarm 23 }


hwFault         OBJECT-TYPE
    SYNTAX 	DisplayString
    MAX-ACCESS 	read-write
    STATUS 	current
    DESCRIPTION 	"Alarm notification configuration for hardware fault. Select one or more of the following: ui icon log beep snmp gc"

    ::= { alarm 24 }


sdiUnlocked     OBJECT-TYPE
    SYNTAX 	DisplayString
    MAX-ACCESS 	read-write
    STATUS 	current
    DESCRIPTION 	"Alarm notification configuration for unlocked SDI input. Select one or more of the following: ui icon log beep snmp gc"

    ::= { alarm 25 }


ltcInvalid      OBJECT-TYPE
    SYNTAX 	DisplayString
    MAX-ACCESS 	read-write
    STATUS 	current
    DESCRIPTION 	"Alarm notification configuration for invalid LTC timecode. Select one or more of the following: ui icon log beep snmp gc"

    ::= { alarm 26 }


vitcInvalid     OBJECT-TYPE
    SYNTAX 	DisplayString
    MAX-ACCESS 	read-write
    STATUS 	current
    DESCRIPTION 	"Alarm notification configuration for invalid VITC timecode. Select one or more of the following: ui icon log beep snmp gc"

    ::= { alarm 27 }


eAudBufferFull  OBJECT-TYPE
    SYNTAX 	DisplayString
    MAX-ACCESS 	read-write
    STATUS 	current
    DESCRIPTION 	"Alarm notification configuration for embedded audio buffer overflow. Select one or more of the following: ui icon log beep snmp gc"

    ::= { alarm 28 }


eAudBufferEmpty OBJECT-TYPE
    SYNTAX 	DisplayString
    MAX-ACCESS 	read-write
    STATUS 	current
    DESCRIPTION 	"Alarm notification configuration for embedded audio buffer overflow. Select one or more of the following: ui icon log beep snmp gc"

    ::= { alarm 29 }

-- alarmStatus(deprecated).

gamutLuma       OBJECT-TYPE
    SYNTAX 	DisplayString
    MAX-ACCESS 	read-write
    STATUS 	current
    DESCRIPTION 	"Alarm notification configuration for luma gamut error. Select one or more of the following: ui icon log beep snmp gc"

    ::= { alarm 31 }


refVideo        OBJECT-TYPE
    SYNTAX 	DisplayString
    MAX-ACCESS 	read-write
    STATUS 	current
    DESCRIPTION 	"Alarm notification configuration for reference video alarm. Select one or more of the following: ui icon log beep snmp gc"

    ::= { alarm 32 }


cableLength     OBJECT-TYPE
    SYNTAX 	DisplayString
    MAX-ACCESS 	read-write
    STATUS 	current
    DESCRIPTION 	"Alarm notification configuration for cable length alarm. Select one or more of the following: ui icon log beep snmp gc"

    ::= { alarm 33 }


srcLevelAlarmConfig OBJECT-TYPE
    SYNTAX 	DisplayString
    MAX-ACCESS 	read-write
    STATUS 	current
    DESCRIPTION 	"Alarm notification configuration for source level alarm. Select one or more of the following: ui icon log beep snmp gc"

    ::= { alarm 34 }


ccTransMissing  OBJECT-TYPE
    SYNTAX 	DisplayString
    MAX-ACCESS 	read-write
    STATUS 	current
    DESCRIPTION 	"Alarm notification configuration for closed caption missing. Select one or more of the following: ui icon log beep snmp gc"

    ::= { alarm 35 }


ancPresence     OBJECT-TYPE
    SYNTAX 	DisplayString
    MAX-ACCESS 	read-write
    STATUS 	current
    DESCRIPTION 	"Alarm notification configuration for ancillary data missing. Select one or more of the following: ui icon log beep snmp gc"

    ::= { alarm 36 }


ancPlacement    OBJECT-TYPE
    SYNTAX 	DisplayString
    MAX-ACCESS 	read-write
    STATUS 	current
    DESCRIPTION 	"Alarm notification configuration for ancillary data placement error. Select one or more of the following: ui icon log beep snmp gc"

    ::= { alarm 37 }


sdiYAncParity   OBJECT-TYPE
    SYNTAX 	DisplayString
    MAX-ACCESS 	read-write
    STATUS 	current
    DESCRIPTION 	"Alarm notification configuration for sdi Y ancillary data parity error. Select one or more of the following: ui icon log beep snmp gc"

    ::= { alarm 38 }


sdiCAncParity   OBJECT-TYPE
    SYNTAX 	DisplayString
    MAX-ACCESS 	read-write
    STATUS 	current
    DESCRIPTION 	"Alarm notification configuration for sdi C ancillary data parity error. Select one or more of the following: ui icon log beep snmp gc"

    ::= { alarm 39 }


sdiCode         OBJECT-TYPE
    SYNTAX 	DisplayString
    MAX-ACCESS 	read-write
    STATUS 	current
    DESCRIPTION 	"Alarm notification configuration for SDI code violation error. Select one or more of the following: ui icon log beep snmp gc"

    ::= { alarm 40 }


sdiData         OBJECT-TYPE
    SYNTAX 	DisplayString
    MAX-ACCESS 	read-write
    STATUS 	current
    DESCRIPTION 	"Alarm notification configuration for SDI data error. Select one or more of the following: ui icon log beep snmp gc"

    ::= { alarm 41 }


sdiField        OBJECT-TYPE
    SYNTAX 	DisplayString
    MAX-ACCESS 	read-write
    STATUS 	current
    DESCRIPTION 	"Alarm notification configuration for SDI field length error. Select one or more of the following: ui icon log beep snmp gc"

    ::= { alarm 42 }


sdiLine         OBJECT-TYPE
    SYNTAX 	DisplayString
    MAX-ACCESS 	read-write
    STATUS 	current
    DESCRIPTION 	"Alarm notification configuration for SDI line length error. Select one or more of the following: ui icon log beep snmp gc"

    ::= { alarm 43 }


sdiHdLine       OBJECT-TYPE
    SYNTAX 	DisplayString
    MAX-ACCESS 	read-write
    STATUS 	current
    DESCRIPTION 	"Alarm notification configuration for 292M line number mismatch. Select one or more of the following: ui icon log beep snmp gc"

    ::= { alarm 44 }


sdiNoEav        OBJECT-TYPE
    SYNTAX 	DisplayString
    MAX-ACCESS 	read-write
    STATUS 	current
    DESCRIPTION 	"Alarm notification configuration for EAV placement error. Select one or more of the following: ui icon log beep snmp gc"

    ::= { alarm 45 }


sdiNoSav        OBJECT-TYPE
    SYNTAX 	DisplayString
    MAX-ACCESS 	read-write
    STATUS 	current
    DESCRIPTION 	"Alarm notification configuration for SAV placement error. Select one or more of the following: ui icon log beep snmp gc"

    ::= { alarm 46 }


sdiBadCrc       OBJECT-TYPE
    SYNTAX 	DisplayString
    MAX-ACCESS 	read-write
    STATUS 	current
    DESCRIPTION 	"Alarm notification configuration for SDI SD CRC error. Select one or more of the following: ui icon log beep snmp gc"

    ::= { alarm 47 }


sdiBadCrcY      OBJECT-TYPE
    SYNTAX 	DisplayString
    MAX-ACCESS 	read-write
    STATUS 	current
    DESCRIPTION 	"Alarm notification configuration for CRC error on SDI HD Y channel. Select one or more of the following: ui icon log beep snmp gc"

    ::= { alarm 48 }


sdiBadCrcC      OBJECT-TYPE
    SYNTAX 	DisplayString
    MAX-ACCESS 	read-write
    STATUS 	current
    DESCRIPTION 	"Alarm notification configuration for CRC error on SDI HD C channel. Select one or more of the following: ui icon log beep snmp gc"

    ::= { alarm 49 }


embAudioChecksum OBJECT-TYPE
    SYNTAX 	DisplayString
    MAX-ACCESS 	read-write
    STATUS 	current
    DESCRIPTION 	"Alarm notification configuration for embedded audio checksum error. Select one or more of the following: ui icon log beep snmp gc"

    ::= { alarm 50 }


aesAudioCode    OBJECT-TYPE
    SYNTAX 	DisplayString
    MAX-ACCESS 	read-write
    STATUS 	current
    DESCRIPTION 	"Alarm notification configuration for AES audio code error. Select one or more of the following: ui icon log beep snmp gc"

    ::= { alarm 51 }


aesAudioAbsent  OBJECT-TYPE
    SYNTAX 	DisplayString
    MAX-ACCESS 	read-write
    STATUS 	current
    DESCRIPTION 	"Alarm notification configuration for AES audio absence. Select one or more of the following: ui icon log beep snmp gc"

    ::= { alarm 52 }


aesAudioFormat  OBJECT-TYPE
    SYNTAX 	DisplayString
    MAX-ACCESS 	read-write
    STATUS 	current
    DESCRIPTION 	"Alarm notification configuration for AES audio format error. Select one or more of the following: ui icon log beep snmp gc"

    ::= { alarm 53 }


aesAudioLowConf OBJECT-TYPE
    SYNTAX 	DisplayString
    MAX-ACCESS 	read-write
    STATUS 	current
    DESCRIPTION 	"Alarm notification configuration for AES audio low confidence error. Select one or more of the following: ui icon log beep snmp gc"

    ::= { alarm 54 }


sdiBadCrcFF     OBJECT-TYPE
    SYNTAX 	DisplayString
    MAX-ACCESS 	read-write
    STATUS 	current
    DESCRIPTION 	"Alarm notification configuration for RP165 full-field CRC error. Select one or more of the following: ui icon log beep snmp gc"

    ::= { alarm 55 }


sdiBadCrcAP     OBJECT-TYPE
    SYNTAX 	DisplayString
    MAX-ACCESS 	read-write
    STATUS 	current
    DESCRIPTION 	"Alarm notification configuration for RP165 active picture CRC error. Select one or more of the following: ui icon log beep snmp gc"

    ::= { alarm 56 }


embAudioAsync   OBJECT-TYPE
    SYNTAX 	DisplayString
    MAX-ACCESS 	read-write
    STATUS 	current
    DESCRIPTION 	"Alarm notification configuration for embedded audio group sample phase. Select one or more of the following: ui icon log beep snmp gc"

    ::= { alarm 57 }


inputSigNotHD   OBJECT-TYPE
    SYNTAX 	DisplayString
    MAX-ACCESS 	read-write
    STATUS 	current
    DESCRIPTION 	"Alarm notification configuration for input signal not HD warning. Select one or more of the following: ui icon log beep snmp gc"

    ::= { alarm 58 }


alarmStatusStr  OBJECT-TYPE
    SYNTAX 	BITS {
        reserved(0),
        ancB39Presence(1),
        vchipChanged(2),
        vchipPresence(3),
        ccProtocol(4),
        ccParityChecksum(5),
        ccSvcMissing(6),
        ccChanged(7),
        embAudioBufferEmpty(8),
        embAudioBufferFull(9),
        ancVitcMissing(10),
        ancVitcInvalid(11),
        srcLevelAlarm(12),
        cableLengthAlarm(13),
        audioPhaseError(14),
        ccActvTransMissing(15),
        jitterAlarm(16),
        eyeUnlockedAlarm(17),
        eyeFallOvershoot(18),
        eyeRiseOvershoot(19),
        eyeRiseFallDelta(20),
        eyeFallTime(21),
        eyeRiseTime(22),
        eyeAmplitude(23),
        aesCrcError(24),
        aesValidBit(25),
        audioLowConfidence(26),
        aesFormat(27),
        aesCodeError(28),
        aesParity(29),
        aesUnlocked(30),
        aesMissing(31),
        embAudioSlip(32),
        embAudioParity(33),
        embAudioCrc(34),
        embAudioStreamMissing(35),
        audioClip(36),
        audioMute(37),
        audioOver(38),
        audioSilence(39),
        sdiYAncParity(40),
        sdiCAncParity(41),
        ancDataPlacement(42),
        ancDataPresence(43),
        sdiHdCAncCksm(44),
        gamutLuma(45),
        gamutRgb(46),
        gamutComposite(47),
        sdiHdYAncCksm(48),
        sdiHdLineNumber(49),
        sdiAudioParity(50),
        sdiAudioMissing(51),
        sdiHdCCrc(52),
        sdiHdYCrc(53),
        sdiSdFfCrc(54),
        sdiSdApCrc(55),
        embAudioStreamChksum(56),
        sdiNoSAV(57),
        sdiNoEAV(58),
        sdiFieldLength(59),
        sdiLineLength(60),
        sdiDataError(61),
        sdiCodeWordViolation(62),
        sdiBadEdh(63),
        extRefFormatMismatch(64),
        systemFault(65),
        hwFault(66),
        overTemperature(67),
        vitcInvalid(68),
        vitcMissing(69),
        ltcInvalid(70),
        ltcMissing(71),
        videoRefFormatMismatch(72),
        videoFormatMismatch(73),
        videoNotHd(74),
        videoFormatChange(75),
        refUnlocked(76),
        refMissing(77),
        inputUnlocked(78),
        videoSignalMissing(79),
        ccCEA608Line21Missing(80),
        smpte334mMissing(81),
        cea608CaptionError(82),
        vchipFormatError(83),
        xdsError(84),
        cdpError(85),
        tsidMissing(86),
        tsidFormatError(87),
        audioFrameSync(88),
        audio-VideoSync(89),
        dolbyFormatMismatch(90),
        dolbyVideoSync(91),
        audEmbedGroupSamplePhase(92),
        jitter2Alarm(93),
        cableLossAlarm(94),
        loudnessChan(95),
        loudnessPgm(96),
        smpte352Missing(97),
        ancB37Missing(98),
        ancB35Missing(99),
        ancB23-1Missing(100),
        ancB23-2Missing(101),
        ancB22Missing(102),
        ancITU1685Missing(103),
        audioCtrlMissing(104),
        dualLinkTimingError(105),
        dualLinkFmtMismatch(106),
        avDelay(107),
        afdMissing(108),
        wssMissing(109),
        viMissing(110),
        dolbyETiming(111),
        dolbyPaAlign(112),
        dolbyCrcError(113),
        wstVbiMissing(114),
        op47Missing(115),
        op47ProtocolError(116),
        eia708ProtocolError(117),
        wstProtocolError(118),
        cc608SvcMissing(119),
        cc708SvcMissing(120),
        ccWstPageMissing(121),
        rp207Error(122),
        copyrightStatus(123),
        copyrightStatusChange(124),
        blackDetected(125),
        frozenFrameDetected(126),
        ancLtcInvalid(127),
        ancLtcMissing(128),
        sourceIdAlarm(129),
        sourceIdChanged(130),
        quietPgm(131),
        loudnessSession(132),
        quietSession(133),
        dialnormMismatch(134),
        aesFrameError(135),
        audioPhase(136),
        refGenLockUnlocked(137),
        hdmiAcpPacketMissing(138),
        hdmiIsrcPacketMissing(139),
        hdmiGamutPacketMissing(140),
        hdmiVendorInfoMissing(141),
        hdmiAviInfoMissing(142),
        hdmiSourceProdInfoMissing(143),
        hdmiAudioInfoMissing(144),
        hdmiMpegSourceInfoMissing(145),
        ancB37Protocol(146),
        ancAribCcMissing(147),
        ancAribCcProtocol(148),
        ancS2031Missing(149),
        ancS2031Protocol(150)
    }
    MAX-ACCESS 	read-only
    STATUS 	current
    DESCRIPTION 	"Returns alarm status.  Each bit in an octet notes the status of one alarm.  If the bit is one the corresponding alarm condition is active."

    ::= { alarm 59 }


videoFmtChange  OBJECT-TYPE
    SYNTAX 	DisplayString
    MAX-ACCESS 	read-write
    STATUS 	current
    DESCRIPTION 	"Alarm notification configuration for video format change warning. Select one or more of the following: ui icon log beep snmp gc"

    ::= { alarm 60 }


videoFmtMismatch OBJECT-TYPE
    SYNTAX 	DisplayString
    MAX-ACCESS 	read-write
    STATUS 	current
    DESCRIPTION 	"Alarm notification configuration for video format mismatch error. The detected input video format does not match the selected format. Select one or more of the following: ui icon log beep snmp gc"

    ::= { alarm 61 }


videoRefFmtMismatch OBJECT-TYPE
    SYNTAX 	DisplayString
    MAX-ACCESS 	read-write
    STATUS 	current
    DESCRIPTION 	"Alarm notification configuration for video/reference format mismatch. The input video format does not match the external reference format. Select one or more of the following: ui icon log beep snmp gc"

    ::= { alarm 62 }


extRefFmtMismatch OBJECT-TYPE
    SYNTAX 	DisplayString
    MAX-ACCESS 	read-write
    STATUS 	current
    DESCRIPTION 	"Alarm notification configuration for ext reference format mismatch. The detected reference format does not match the selected format. Select one or more of the following: ui icon log beep snmp gc"

    ::= { alarm 63 }


eyeAmp          OBJECT-TYPE
    SYNTAX 	DisplayString
    MAX-ACCESS 	read-write
    STATUS 	current
    DESCRIPTION 	"Alarm notification configuration for eye amplitude threshold violation. Select one or more of the following: ui icon log beep snmp gc"

    ::= { alarm 64 }


eyeRise         OBJECT-TYPE
    SYNTAX 	DisplayString
    MAX-ACCESS 	read-write
    STATUS 	current
    DESCRIPTION 	"Alarm notification configuration for eye rise time threshold violation. Select one or more of the following: ui icon log beep snmp gc"

    ::= { alarm 65 }


eyeFall         OBJECT-TYPE
    SYNTAX 	DisplayString
    MAX-ACCESS 	read-write
    STATUS 	current
    DESCRIPTION 	"Alarm notification configuration for eye fall time threshold violation. Select one or more of the following: ui icon log beep snmp gc"

    ::= { alarm 66 }


eyeRiseFallDeltaAlarm OBJECT-TYPE
    SYNTAX 	DisplayString
    MAX-ACCESS 	read-write
    STATUS 	current
    DESCRIPTION 	"Alarm notification configuration for eye rise/fall delta threshold violation. Select one or more of the following: ui icon log beep snmp gc"

    ::= { alarm 67 }


eyeRiseOversht  OBJECT-TYPE
    SYNTAX 	DisplayString
    MAX-ACCESS 	read-write
    STATUS 	current
    DESCRIPTION 	"Alarm notification configuration for eye overshoot threshold violation. Select one or more of the following: ui icon log beep snmp gc"

    ::= { alarm 68 }


eyeFallOversht  OBJECT-TYPE
    SYNTAX 	DisplayString
    MAX-ACCESS 	read-write
    STATUS 	current
    DESCRIPTION 	"Alarm notification configuration for eye undershoot threshold violation. Select one or more of the following: ui icon log beep snmp gc"

    ::= { alarm 69 }


jitLevel        OBJECT-TYPE
    SYNTAX 	DisplayString
    MAX-ACCESS 	read-write
    STATUS 	current
    DESCRIPTION 	"Alarm notification configuration for jitter measurement threshold violation. Select one or more of the following: ui icon log beep snmp gc"

    ::= { alarm 70 }


ccChanged       OBJECT-TYPE
    SYNTAX 	DisplayString
    MAX-ACCESS 	read-write
    STATUS 	current
    DESCRIPTION 	"Alarm notification configuration for closed caption status change. Select one or more of the following: ui icon log beep snmp gc"

    ::= { alarm 71 }


ccParityCksm    OBJECT-TYPE
    SYNTAX 	DisplayString
    MAX-ACCESS 	read-write
    STATUS 	current
    DESCRIPTION 	"Alarm notification configuration for CC parity/checksum error. Select one or more of the following: ui icon log beep snmp gc"

    ::= { alarm 72 }


ccProtocol      OBJECT-TYPE
    SYNTAX 	DisplayString
    MAX-ACCESS 	read-write
    STATUS 	current
    DESCRIPTION 	"Alarm notification configuration for closed caption protocol error. Select one or more of the following: ui icon log beep snmp gc"

    ::= { alarm 73 }


vchipPresence   OBJECT-TYPE
    SYNTAX 	DisplayString
    MAX-ACCESS 	read-write
    STATUS 	current
    DESCRIPTION 	"Alarm notification configuration for V-chip data missing. Select one or more of the following: ui icon log beep snmp gc"

    ::= { alarm 74 }


vchipRating     OBJECT-TYPE
    SYNTAX 	DisplayString
    MAX-ACCESS 	read-write
    STATUS 	current
    DESCRIPTION 	"Alarm notification configuration for V-chip ratings change. Select one or more of the following: ui icon log beep snmp gc"

    ::= { alarm 75 }


ccSvcMissing    OBJECT-TYPE
    SYNTAX 	DisplayString
    MAX-ACCESS 	read-write
    STATUS 	deprecated
    DESCRIPTION 	"Alarm notification configuration for closed caption service missing. Select one or more of the following: ui icon log beep snmp gc"

    ::= { alarm 76 }


ancB39Pres      OBJECT-TYPE
    SYNTAX 	DisplayString
    MAX-ACCESS 	read-write
    STATUS 	current
    DESCRIPTION 	"Alarm notification configuration for ARIB B.39 packet missing. Select one or more of the following: ui icon log beep snmp gc"

    ::= { alarm 77 }


sdiBadCksmYAnc  OBJECT-TYPE
    SYNTAX 	DisplayString
    MAX-ACCESS 	read-write
    STATUS 	current
    DESCRIPTION 	"Alarm notification configuration for checksum error in Y channel ANC data. Select one or more of the following: ui icon log beep snmp gc"

    ::= { alarm 78 }


sdiBadCksmCAnc  OBJECT-TYPE
    SYNTAX 	DisplayString
    MAX-ACCESS 	read-write
    STATUS 	current
    DESCRIPTION 	"Alarm notification configuration for checksum error in C channel ANC data. Select one or more of the following: ui icon log beep snmp gc"

    ::= { alarm 79 }


ancVitcInvalid  OBJECT-TYPE
    SYNTAX 	DisplayString
    MAX-ACCESS 	read-write
    STATUS 	current
    DESCRIPTION 	"Alarm notification configuration for invalid ancillary VITC. Select one or more of the following: ui icon log beep snmp gc"

    ::= { alarm 80 }


ancVitcMissing  OBJECT-TYPE
    SYNTAX 	DisplayString
    MAX-ACCESS 	read-write
    STATUS 	current
    DESCRIPTION 	"Alarm notification configuration for ancillary VITC missing. Select one or more of the following: ui icon log beep snmp gc"

    ::= { alarm 81 }


ccCEA608Line21Missing OBJECT-TYPE
    SYNTAX 	DisplayString
    MAX-ACCESS 	read-write
    STATUS 	current
    DESCRIPTION 	"Alarm notification configuration for CC CEA608 Line21 missing. Select one or more of the following: ui icon log beep snmp gc"

    ::= { alarm 82 }


smpte334mMissing OBJECT-TYPE
    SYNTAX 	DisplayString
    MAX-ACCESS 	read-write
    STATUS 	current
    DESCRIPTION 	"Alarm notification configuration for SMPTE 334M Anc missing. Select one or more of the following: ui icon log beep snmp gc"

    ::= { alarm 83 }


cea608CaptionError OBJECT-TYPE
    SYNTAX 	DisplayString
    MAX-ACCESS 	read-write
    STATUS 	current
    DESCRIPTION 	"Alarm notification configuration for CEA608 caption error. Select one or more of the following: ui icon log beep snmp gc"

    ::= { alarm 84 }


vChipFormatError OBJECT-TYPE
    SYNTAX 	DisplayString
    MAX-ACCESS 	read-write
    STATUS 	current
    DESCRIPTION 	"Alarm notification configuration for vchip format error. Select one or more of the following: ui icon log beep snmp gc"

    ::= { alarm 85 }


xdsError        OBJECT-TYPE
    SYNTAX 	DisplayString
    MAX-ACCESS 	read-write
    STATUS 	current
    DESCRIPTION 	"Alarm notification configuration for Extended Data Services error. Select one or more of the following: ui icon log beep snmp gc"

    ::= { alarm 86 }


cdpError        OBJECT-TYPE
    SYNTAX 	DisplayString
    MAX-ACCESS 	read-write
    STATUS 	current
    DESCRIPTION 	"Alarm notification configuration for Caption Data Packet error. Select one or more of the following: ui icon log beep snmp gc"

    ::= { alarm 87 }


tsidMissing     OBJECT-TYPE
    SYNTAX 	DisplayString
    MAX-ACCESS 	read-write
    STATUS 	current
    DESCRIPTION 	"Alarm notification configuration for TSID missing. Select one or more of the following: ui icon log beep snmp gc"

    ::= { alarm 88 }


tsidFormatError OBJECT-TYPE
    SYNTAX 	DisplayString
    MAX-ACCESS 	read-write
    STATUS 	current
    DESCRIPTION 	"Alarm notification configuration for TSID format error. Select one or more of the following: ui icon log beep snmp gc"

    ::= { alarm 89 }


audioFrameSync  OBJECT-TYPE
    SYNTAX 	DisplayString
    MAX-ACCESS 	read-write
    STATUS 	current
    DESCRIPTION 	"Alarm notification configuration for AES frame sync error. Select one or more of the following: ui icon log beep snmp gc"

    ::= { alarm 90 }


audio-VideoSync OBJECT-TYPE
    SYNTAX 	DisplayString
    MAX-ACCESS 	read-write
    STATUS 	current
    DESCRIPTION 	"Alarm notification configuration for Audio-Video sync error. Select one or more of the following: ui icon log beep snmp gc"

    ::= { alarm 91 }


dolbyFormatMismatch OBJECT-TYPE
    SYNTAX 	DisplayString
    MAX-ACCESS 	read-write
    STATUS 	current
    DESCRIPTION 	"Alarm notification configuration for Dolby format mismatch. Select one or more of the following: ui icon log beep snmp gc"

    ::= { alarm 92 }


dolbyVideoSync  OBJECT-TYPE
    SYNTAX 	DisplayString
    MAX-ACCESS 	read-write
    STATUS 	current
    DESCRIPTION 	"Alarm notification configuration for Dolby E Video Sync error. Select one or more of the following: ui icon log beep snmp gc"

    ::= { alarm 93 }


audEmbedGroupSamplePhase OBJECT-TYPE
    SYNTAX 	DisplayString
    MAX-ACCESS 	read-write
    STATUS 	current
    DESCRIPTION 	"Alarm notification configuration for embedded audio sample phase errors between selected groups. Select one or more of the following: ui icon log beep snmp gc"

    ::= { alarm 94 }


jit2Level       OBJECT-TYPE
    SYNTAX 	DisplayString
    MAX-ACCESS 	read-write
    STATUS 	current
    DESCRIPTION 	"Alarm notification configuration for the second jitter measurement engine. Select one or more of the following: ui icon log beep snmp gc"

    ::= { alarm 95 }


cableLossAlrmCfg OBJECT-TYPE
    SYNTAX 	DisplayString
    MAX-ACCESS 	read-write
    STATUS 	current
    DESCRIPTION 	"Alarm notification configuration for cable loss alarm. Select one or more of the following: ui icon log beep snmp gc"

    ::= { alarm 96 }


eyeUnlckAlrmCfg OBJECT-TYPE
    SYNTAX 	DisplayString
    MAX-ACCESS 	read-write
    STATUS 	current
    DESCRIPTION 	"Alarm notification configuration for eye unlocked alarm. Select one or more of the following: ui icon log beep snmp gc"

    ::= { alarm 97 }


audLoudnessChan OBJECT-TYPE
    SYNTAX 	DisplayString
    MAX-ACCESS 	read-write
    STATUS 	current
    DESCRIPTION 	"Alarm notification configuration for loudness channel. Select one or more of the following: ui icon log beep snmp gc"

    ::= { alarm 98 }


audLoudnessPgm  OBJECT-TYPE
    SYNTAX 	DisplayString
    MAX-ACCESS 	read-write
    STATUS 	current
    DESCRIPTION 	"Alarm notification configuration for loudness program. Select one or more of the following: ui icon log beep snmp gc"

    ::= { alarm 99 }


smpte352Missing OBJECT-TYPE
    SYNTAX 	DisplayString
    MAX-ACCESS 	read-write
    STATUS 	current
    DESCRIPTION 	"Alarm notification configuration for SMPTE 352 missing alarm. Select one or more of the following: ui icon log beep snmp gc"

    ::= { alarm 100 }


audCtrlPktMissing OBJECT-TYPE
    SYNTAX 	DisplayString
    MAX-ACCESS 	read-write
    STATUS 	current
    DESCRIPTION 	"Alarm notification configuration for Audio control Packet missing alarm. Select one or more of the following: ui icon log beep snmp gc"

    ::= { alarm 101 }


ancB37Missing   OBJECT-TYPE
    SYNTAX 	DisplayString
    MAX-ACCESS 	read-write
    STATUS 	current
    DESCRIPTION 	"Alarm notification configuration for ancB37Missing alarm. Select one or more of the following: ui icon log beep snmp gc"

    ::= { alarm 102 }


ancB35Missing   OBJECT-TYPE
    SYNTAX 	DisplayString
    MAX-ACCESS 	read-write
    STATUS 	current
    DESCRIPTION 	"Alarm notification configuration for ancB35Missing alarm. Select one or more of the following: ui icon log beep snmp gc"

    ::= { alarm 103 }


ancB23-1Missing OBJECT-TYPE
    SYNTAX 	DisplayString
    MAX-ACCESS 	read-write
    STATUS 	current
    DESCRIPTION 	"Alarm notification configuration for ancB23-1Missing alarm. Select one or more of the following: ui icon log beep snmp gc"

    ::= { alarm 104 }


ancB23-2Missing OBJECT-TYPE
    SYNTAX 	DisplayString
    MAX-ACCESS 	read-write
    STATUS 	current
    DESCRIPTION 	"Alarm notification configuration for ancB23-2Missing alarm. Select one or more of the following: ui icon log beep snmp gc"

    ::= { alarm 105 }


ancB22Missing   OBJECT-TYPE
    SYNTAX 	DisplayString
    MAX-ACCESS 	read-write
    STATUS 	current
    DESCRIPTION 	"Alarm notification configuration for ancB22Missing alarm. Select one or more of the following: ui icon log beep snmp gc"

    ::= { alarm 106 }


ancITU1685Missing OBJECT-TYPE
    SYNTAX 	DisplayString
    MAX-ACCESS 	read-write
    STATUS 	current
    DESCRIPTION 	"Alarm notification configuration for ancITU1685Missing alarm. Select one or more of the following: ui icon log beep snmp gc"

    ::= { alarm 107 }


dualLinkTimingError OBJECT-TYPE
    SYNTAX 	DisplayString
    MAX-ACCESS 	read-write
    STATUS 	current
    DESCRIPTION 	"Alarm notification configuration for timing reference dual link alarm. Select one or more of the following: ui icon log beep snmp gc"

    ::= { alarm 108 }


dualLinkFmtMismatch OBJECT-TYPE
    SYNTAX 	DisplayString
    MAX-ACCESS 	read-write
    STATUS 	current
    DESCRIPTION 	"Alarm notification configuration for dual link format mismatch alarm. Select one or more of the following: ui icon log beep snmp gc"

    ::= { alarm 109 }


avDelay         OBJECT-TYPE
    SYNTAX 	DisplayString
    MAX-ACCESS 	read-write
    STATUS 	current
    DESCRIPTION 	"Alarm notification configuration for AV delay value alarm. Select one or more of the following: ui icon log beep snmp gc"

    ::= { alarm 110 }


afdMissing      OBJECT-TYPE
    SYNTAX 	DisplayString
    MAX-ACCESS 	read-write
    STATUS 	current
    DESCRIPTION 	"Alarm notification configuration for AFD missing alarm. Select one or more of the following: ui icon log beep snmp gc"

    ::= { alarm 111 }


wssMissing      OBJECT-TYPE
    SYNTAX 	DisplayString
    MAX-ACCESS 	read-write
    STATUS 	current
    DESCRIPTION 	"Alarm notification configuration for WSS missing alarm. Select one or more of the following: ui icon log beep snmp gc"

    ::= { alarm 112 }


viMissing       OBJECT-TYPE
    SYNTAX 	DisplayString
    MAX-ACCESS 	read-write
    STATUS 	current
    DESCRIPTION 	"Alarm notification configuration for Video Index missing alarm. Select one or more of the following: ui icon log beep snmp gc"

    ::= { alarm 113 }


dolbyETiming    OBJECT-TYPE
    SYNTAX 	DisplayString
    MAX-ACCESS 	read-write
    STATUS 	current
    DESCRIPTION 	"Alarm notification configuration for Dolby E Video timing alarm. Select one or more of the following: ui icon log beep snmp gc"

    ::= { alarm 114 }


dolbyPaAlign    OBJECT-TYPE
    SYNTAX 	DisplayString
    MAX-ACCESS 	read-write
    STATUS 	current
    DESCRIPTION 	"Alarm notification configuration for Dolby PA alignment alarm. Select one or more of the following: ui icon log beep snmp gc"

    ::= { alarm 115 }


dolbyCrcError   OBJECT-TYPE
    SYNTAX 	DisplayString
    MAX-ACCESS 	read-write
    STATUS 	current
    DESCRIPTION 	"Alarm notification configuration for Dolby CRC error alarm. Select one or more of the following: ui icon log beep snmp gc"

    ::= { alarm 116 }


wstVbiMissing   OBJECT-TYPE
    SYNTAX 	DisplayString
    MAX-ACCESS 	read-write
    STATUS 	current
    DESCRIPTION 	"Alarm notification configuration for VBI(WST) missing alarm. Select one or more of the following: ui icon log beep snmp gc"

    ::= { alarm 117 }


op47Missing     OBJECT-TYPE
    SYNTAX 	DisplayString
    MAX-ACCESS 	read-write
    STATUS 	current
    DESCRIPTION 	"Alarm notification configuration for OP47 anc teletext missing alarm. Select one or more of the following: ui icon log beep snmp gc"

    ::= { alarm 118 }


op47ProtocolError OBJECT-TYPE
    SYNTAX 	DisplayString
    MAX-ACCESS 	read-write
    STATUS 	current
    DESCRIPTION 	"Alarm notification configuration for OP47 protocol error alarm. Select one or more of the following: ui icon log beep snmp gc"

    ::= { alarm 119 }


eia708ProtocolError OBJECT-TYPE
    SYNTAX 	DisplayString
    MAX-ACCESS 	read-write
    STATUS 	current
    DESCRIPTION 	"Alarm notification configuration for EIA708 protocol error alarm. Select one or more of the following: ui icon log beep snmp gc"

    ::= { alarm 120 }


wstProtocolError OBJECT-TYPE
    SYNTAX 	DisplayString
    MAX-ACCESS 	read-write
    STATUS 	current
    DESCRIPTION 	"Alarm notification configuration for WST protocol error alarm. Select one or more of the following: ui icon log beep snmp gc"

    ::= { alarm 121 }


cc608SvcMissing OBJECT-TYPE
    SYNTAX 	DisplayString
    MAX-ACCESS 	read-write
    STATUS 	current
    DESCRIPTION 	"Alarm notification configuration for CEA608 service missing alarm.  Select one or more of the following: ui icon log beep snmp gc"

    ::= { alarm 122 }


cc708SvcMissing OBJECT-TYPE
    SYNTAX 	DisplayString
    MAX-ACCESS 	read-write
    STATUS 	current
    DESCRIPTION 	"Alarm notification configuration for CEA708 service missing alarm.  Select one or more of the following: ui icon log beep snmp gc"

    ::= { alarm 123 }


ccWstPageMissing OBJECT-TYPE
    SYNTAX 	DisplayString
    MAX-ACCESS 	read-write
    STATUS 	current
    DESCRIPTION 	"Alarm notification configuration for teletext pages missing alarm.  Select one or more of the following: ui icon log beep snmp gc"

    ::= { alarm 124 }


rp207Error      OBJECT-TYPE
    SYNTAX 	DisplayString
    MAX-ACCESS 	read-write
    STATUS 	current
    DESCRIPTION 	"Alarm notification configuration for RP207 protocol error.  Select one or more of the following: ui icon log beep snmp gc"

    ::= { alarm 125 }


copyrightStatus OBJECT-TYPE
    SYNTAX 	DisplayString
    MAX-ACCESS 	read-write
    STATUS 	current
    DESCRIPTION 	"Alarm notification configuration for copyright status error.  Select one or more of the following: ui icon log beep snmp gc"

    ::= { alarm 126 }


copyrightStatusChange OBJECT-TYPE
    SYNTAX 	DisplayString
    MAX-ACCESS 	read-write
    STATUS 	current
    DESCRIPTION 	"Alarm notification configuration for copyright status change.  Select one or more of the following: ui icon log beep snmp gc"

    ::= { alarm 127 }


blackDetectConfig OBJECT-TYPE
    SYNTAX 	DisplayString
    MAX-ACCESS 	read-write
    STATUS 	current
    DESCRIPTION 	"Alarm notification configuration for black detect. Select one or more of the following: ui icon log beep snmp gc"

    ::= { alarm 128 }


frozenFrameDetectConfig OBJECT-TYPE
    SYNTAX 	DisplayString
    MAX-ACCESS 	read-write
    STATUS 	current
    DESCRIPTION 	"Alarm notification configuration for frozen frame detect. Select one or more of the following: ui icon log beep snmp gc"

    ::= { alarm 129 }


ancLtcInvalid   OBJECT-TYPE
    SYNTAX 	DisplayString
    MAX-ACCESS 	read-write
    STATUS 	current
    DESCRIPTION 	"Alarm notification configuration for invalid ancillary LTC. Select one or more of the following: ui icon log beep snmp gc"

    ::= { alarm 130 }


ancLtcMissing   OBJECT-TYPE
    SYNTAX 	DisplayString
    MAX-ACCESS 	read-write
    STATUS 	current
    DESCRIPTION 	"Alarm notification configuration for ancillary LTC missing. Select one or more of the following: ui icon log beep snmp gc"

    ::= { alarm 131 }


sourceIdAlarm   OBJECT-TYPE
    SYNTAX 	DisplayString
    MAX-ACCESS 	read-write
    STATUS 	current
    DESCRIPTION 	"Alarm notification configuration for Source ID error. Select one or more of the following: ui icon log beep snmp gc"

    ::= { alarm 132 }


sourceIdChanged OBJECT-TYPE
    SYNTAX 	DisplayString
    MAX-ACCESS 	read-write
    STATUS 	current
    DESCRIPTION 	"Alarm notification configuration for Source ID changed. Select one or more of the following: ui icon log beep snmp gc"

    ::= { alarm 133 }


audQuietProgram OBJECT-TYPE
    SYNTAX 	DisplayString
    MAX-ACCESS 	read-write
    STATUS 	current
    DESCRIPTION 	"Alarm notification configuration for program quiet. Select one or more of the following: ui icon log beep snmp gc"

    ::= { alarm 134 }


audLoudnessSession OBJECT-TYPE
    SYNTAX 	DisplayString
    MAX-ACCESS 	read-write
    STATUS 	current
    DESCRIPTION 	"Alarm notification configuration for session loudness. Select one or more of the following: ui icon log beep snmp gc"

    ::= { alarm 135 }


audQuietSession OBJECT-TYPE
    SYNTAX 	DisplayString
    MAX-ACCESS 	read-write
    STATUS 	current
    DESCRIPTION 	"Alarm notification configuration for session quiet. Select one or more of the following: ui icon log beep snmp gc"

    ::= { alarm 136 }


audDialnormMismatch OBJECT-TYPE
    SYNTAX 	DisplayString
    MAX-ACCESS 	read-write
    STATUS 	current
    DESCRIPTION 	"Alarm notification configuration for dialnorm mismatch. Select one or more of the following: ui icon log beep snmp gc"

    ::= { alarm 137 }


aesFrame        OBJECT-TYPE
    SYNTAX 	DisplayString
    MAX-ACCESS 	read-write
    STATUS 	current
    DESCRIPTION 	"Alarm notification configuration for AES Z-preamble error. Select one or more of the following: ui icon log beep snmp gc"

    ::= { alarm 138 }


audioPhase      OBJECT-TYPE
    SYNTAX 	DisplayString
    MAX-ACCESS 	read-write
    STATUS 	current
    DESCRIPTION 	"Alarm notification configuration for audio phase error. Select one or more of the following: ui icon log beep snmp gc"

    ::= { alarm 139 }


refGenLockUnlocked OBJECT-TYPE
    SYNTAX 	DisplayString
    MAX-ACCESS 	read-write
    STATUS 	current
    DESCRIPTION 	"Alarm notification configuration for reference Genlock Unlocked."

    ::= { alarm 140 }


hdmiAcpPacketMissing OBJECT-TYPE
    SYNTAX 	DisplayString
    MAX-ACCESS 	read-write
    STATUS 	current
    DESCRIPTION 	"Alarm notification configuration for HDMI ACP InfoFrame Missing."

    ::= { alarm 141 }


hdmiIsrcPacketMissing OBJECT-TYPE
    SYNTAX 	DisplayString
    MAX-ACCESS 	read-write
    STATUS 	current
    DESCRIPTION 	"Alarm notification configuration for HDMI ISRC Packet Missing."

    ::= { alarm 142 }


hdmiGamutPacketMissing OBJECT-TYPE
    SYNTAX 	DisplayString
    MAX-ACCESS 	read-write
    STATUS 	current
    DESCRIPTION 	"Alarm notification configuration for HDMI Gamut Packet Missing."

    ::= { alarm 143 }


hdmiVendorInfoMissing OBJECT-TYPE
    SYNTAX 	DisplayString
    MAX-ACCESS 	read-write
    STATUS 	current
    DESCRIPTION 	"Alarm notification configuration for HDMI Vendor Specific InfoFrame Missing."

    ::= { alarm 144 }


hdmiAviInfoMissing OBJECT-TYPE
    SYNTAX 	DisplayString
    MAX-ACCESS 	read-write
    STATUS 	current
    DESCRIPTION 	"Alarm notification configuration for HDMI AVI InfoFrame Missing."

    ::= { alarm 145 }


hdmiSourceProdInfoMissing OBJECT-TYPE
    SYNTAX 	DisplayString
    MAX-ACCESS 	read-write
    STATUS 	current
    DESCRIPTION 	"Alarm notification configuration for HDMI Source Product Description InfoFrame Missing."

    ::= { alarm 146 }


hdmiAudioInfoMissing OBJECT-TYPE
    SYNTAX 	DisplayString
    MAX-ACCESS 	read-write
    STATUS 	current
    DESCRIPTION 	"Alarm notification configuration for HDMI Audio InfoFrame Missing."

    ::= { alarm 147 }


hdmiMpegSourceInfoMissing OBJECT-TYPE
    SYNTAX 	DisplayString
    MAX-ACCESS 	read-write
    STATUS 	current
    DESCRIPTION 	"Alarm notification configuration for HDMI MPEG Source InfoFrame Missing."

    ::= { alarm 148 }


ancB37Protocol  OBJECT-TYPE
    SYNTAX 	DisplayString
    MAX-ACCESS 	read-write
    STATUS 	current
    DESCRIPTION 	"Alarm notification configuration for ancB37Protocol alarm. Select one or more of the following: ui icon log beep snmp gc"

    ::= { alarm 149 }


ancAribCcMissing OBJECT-TYPE
    SYNTAX 	DisplayString
    MAX-ACCESS 	read-write
    STATUS 	current
    DESCRIPTION 	"Alarm notification configuration for ancAribCcMissing alarm. Select one or more of the following: ui icon log beep snmp gc"

    ::= { alarm 150 }


ancAribCcProtocol OBJECT-TYPE
    SYNTAX 	DisplayString
    MAX-ACCESS 	read-write
    STATUS 	current
    DESCRIPTION 	"Alarm notification configuration for ancAribCcProtocol alarm. Select one or more of the following: ui icon log beep snmp gc"

    ::= { alarm 151 }


ancS2031Missing OBJECT-TYPE
    SYNTAX 	DisplayString
    MAX-ACCESS 	read-write
    STATUS 	current
    DESCRIPTION 	"Alarm notification configuration for ancS2031Missing alarm. Select one or more of the following: ui icon log beep snmp gc"

    ::= { alarm 152 }


ancS2031Protocol OBJECT-TYPE
    SYNTAX 	DisplayString
    MAX-ACCESS 	read-write
    STATUS 	current
    DESCRIPTION 	"Alarm notification configuration for ancS2031Protocol alarm. Select one or more of the following: ui icon log beep snmp gc"

    ::= { alarm 153 }

-- 
-- ltc group
-- LTC Waveform mode variables

ltcHorPos       OBJECT-TYPE
    SYNTAX 	DisplayString
    MAX-ACCESS 	read-write
    STATUS 	current
    DESCRIPTION 	"LTC waveform horizontal position. Range -1.0 to +1.0,  Relative Offset."

    ::= { ltcEntry 1 }


ltcVertPos      OBJECT-TYPE
    SYNTAX 	DisplayString
    MAX-ACCESS 	read-write
    STATUS 	current
    DESCRIPTION 	"LTC waveform vertical position, Range -12.0 V to +12.0 V"

    ::= { ltcEntry 2 }


ltcGain         OBJECT-TYPE
    SYNTAX 	INTEGER {
        gain-x1(0),
        gain-x5(1),
        gain-x2(2)
    }
    MAX-ACCESS 	read-write
    STATUS 	current
    DESCRIPTION 	"LTC waveform fixed gain"

    ::= { ltcEntry 3 }


ltcVarGainEnable OBJECT-TYPE
    SYNTAX 	INTEGER {
        off(0),
        on(1)
    }
    MAX-ACCESS 	read-write
    STATUS 	current
    DESCRIPTION 	"Enable/disable LTC variable gain"

    ::= { ltcEntry 4 }


ltcVarGain      OBJECT-TYPE
    SYNTAX 	DisplayString
    MAX-ACCESS 	read-write
    STATUS 	current
    DESCRIPTION 	"LTC variable gain value (effective).  Range of values depend.  on current value of ltcGain."

    ::= { ltcEntry 5 }


ltcHMag         OBJECT-TYPE
    SYNTAX 	INTEGER {
        off(0),
        on(1),
        gain-x10(10),
        gain-x20(20),
        gain-x25(25)
    }
    MAX-ACCESS 	read-write
    STATUS 	current
    DESCRIPTION 	"Enable/disable LTC waveform horizontal magnification"

    ::= { ltcEntry 6 }


ltcCenter       OBJECT-TYPE
    SYNTAX 	INTEGER {
        off(0),
        on(1)
    }
    MAX-ACCESS 	read-write
    STATUS 	current
    DESCRIPTION 	"Center LTC waveform (write only)"

    ::= { ltcEntry 7 }


ltcTable        OBJECT-TYPE
    SYNTAX 	SEQUENCE OF LtcEntry
    MAX-ACCESS 	not-accessible
    STATUS 	current
    DESCRIPTION 	"Table for LTC display mode"

    ::= { ltc 1 }


ltcEntry        OBJECT-TYPE
    SYNTAX 	LtcEntry
    MAX-ACCESS 	not-accessible
    STATUS 	current
    DESCRIPTION 	"A row in the ltc table "
    INDEX { currTile }

    ::= { ltcTable 1 }


LtcEntry ::= SEQUENCE {
    ltcHorPos 	DisplayString,
    ltcVertPos 	DisplayString,
    ltcGain 	INTEGER,
    ltcVarGainEnable 	INTEGER,
    ltcVarGain 	DisplayString,
    ltcHMag 	INTEGER,
    ltcCenter 	INTEGER 
}
-- 
-- timing Group
-- Timing display variables

timingH         OBJECT-TYPE
    SYNTAX 	DisplayString
    MAX-ACCESS 	read-only
    STATUS 	current
    DESCRIPTION 	"Horizontal portion of the timing offset in microseconds."

    ::= { timing 1 }


timingV         OBJECT-TYPE
    SYNTAX 	DisplayString
    MAX-ACCESS 	read-only
    STATUS 	current
    DESCRIPTION 	"Vertical portion of the timing offset in lines"

    ::= { timing 2 }


relativeTo      OBJECT-TYPE
    SYNTAX 	INTEGER {
        analog-DAC(0),
        userOffset(1),
        serial-OH(2)
    }
    MAX-ACCESS 	read-write
    STATUS 	current
    DESCRIPTION 	"Selects zero reference for reference timing measurements. "

    ::= { timing 3 }


saveOffset      OBJECT-TYPE
    SYNTAX 	INTEGER
    MAX-ACCESS 	read-write
    STATUS 	current
    DESCRIPTION 	"Saves user current offset between input and reference as zero reference value for use as userOffset (write-only)"

    ::= { timing 4 }


timingReference OBJECT-TYPE
    SYNTAX 	INTEGER {
        ext-reference(0),
        other-input(1)
    }
    MAX-ACCESS 	read-write
    STATUS 	current
    DESCRIPTION 	"Select timing reference in simultaneous input mode."

    ::= { timing 5 }


dualLinkTiming  OBJECT-TYPE
    SYNTAX 	DisplayString
    MAX-ACCESS 	read-only
    STATUS 	current
    DESCRIPTION 	"Link B to Link A timing reference offset measured in ns and clocks"

    ::= { timing 6 }


quadLinkTimingIndex OBJECT-TYPE
    SYNTAX 	INTEGER {
        linkB(1),
        linkC(2),
        linkD(3)
    }
    MAX-ACCESS 	not-accessible
    STATUS 	current
    DESCRIPTION 	"quad link timing Index.  This variable is an index for quadLinkTimingTableIndex value linkX gives relation between linkA and linkX"

    ::= { timing 7 }


linkTimingFor4K OBJECT-TYPE
    SYNTAX 	DisplayString
    MAX-ACCESS 	read-only
    STATUS 	current
    DESCRIPTION 	"linkX to linkA timing reference offset measured in ns and clocks"

    ::= { quadLinkInEntry 1 }


linkToOthersTimingH OBJECT-TYPE
    SYNTAX 	DisplayString
    MAX-ACCESS 	read-only
    STATUS 	current
    DESCRIPTION 	"linkX to linkA Horizontal portion of the timing offset in microseconds"

    ::= { quadLinkInEntry 2 }


linkToOthersTimingV OBJECT-TYPE
    SYNTAX 	DisplayString
    MAX-ACCESS 	read-only
    STATUS 	current
    DESCRIPTION 	"linkX to linkA Vertical portion of the timing offset in lines"

    ::= { quadLinkInEntry 3 }


quadLinkTiming  OBJECT-TYPE
    SYNTAX 	SEQUENCE OF QuadLinkInEntry
    MAX-ACCESS 	not-accessible
    STATUS 	current
    DESCRIPTION 	"Table for quad link Timing Measure"

    ::= { timing 8 }


quadLinkInEntry OBJECT-TYPE
    SYNTAX 	QuadLinkInEntry
    MAX-ACCESS 	not-accessible
    STATUS 	current
    DESCRIPTION 	"A row in the quadLinkTiming Table"
    INDEX { quadLinkTimingIndex }

    ::= { quadLinkTiming 1 }


QuadLinkInEntry ::= SEQUENCE {
    linkTimingFor4K 	DisplayString,
    linkToOthersTimingH 	DisplayString,
    linkToOthersTimingV 	DisplayString 
}
-- 
-- audioAnaDisp group
-- Audio Analog Display variables

audAnaCurOutput OBJECT-TYPE
    SYNTAX 	DisplayString
    MAX-ACCESS 	read-only
    STATUS 	current
    DESCRIPTION 	"Currently selected analog outputs."

    ::= { audioAnaDisp 1 }


audAnaBallistic OBJECT-TYPE
    SYNTAX 	INTEGER {
        truePeak(0),
        ppm1(1),
        ppm2(2),
        vu(3),
        loudness-F(4),
        loudness-S(5)
    }
    MAX-ACCESS 	read-write
    STATUS 	current
    DESCRIPTION 	"Level Meter ballistics selection for analog audio."

    ::= { audioAnaDisp 2 }


audAnaPkHold    OBJECT-TYPE
    SYNTAX 	INTEGER {
        hold-0P1sec(0),
        hold-0P2sec(1),
        hold-0P4sec(2),
        hold-0P8sec(3),
        hold-1sec(4),
        hold-2sec(5),
        hold-3sec(6),
        hold-4sec(7),
        hold-5sec(8),
        hold-6sec(9),
        hold-7sec(10),
        hold-8sec(11),
        hold-9sec(12),
        hold-10sec(13),
        infinity(14)
    }
    MAX-ACCESS 	read-write
    STATUS 	current
    DESCRIPTION 	"Hold time for analog audio peak level indicator (in seconds)."

    ::= { audioAnaDisp 3 }


audAnaErrorHoldTm OBJECT-TYPE
    SYNTAX 	INTEGER (1..30)
    MAX-ACCESS 	read-write
    STATUS 	current
    DESCRIPTION 	"The length of time that the analog audio in-bar error messages and over indicators remain on the screen (held) after the error has been removed (in seconds)."

    ::= { audioAnaDisp 4 }


audAnaOverLvl   OBJECT-TYPE
    SYNTAX 	INTEGER (-6..24)
    MAX-ACCESS 	read-write
    STATUS 	current
    DESCRIPTION 	"Analog audio threshold level for over-volume detection in dBu."

    ::= { audioAnaDisp 5 }


audAnaOverTm    OBJECT-TYPE
    SYNTAX 	INTEGER (0..30)
    MAX-ACCESS 	read-write
    STATUS 	current
    DESCRIPTION 	"Analog audio over volume duration threshold (in seconds)."

    ::= { audioAnaDisp 6 }


audAnaSilenceLvl OBJECT-TYPE
    SYNTAX 	INTEGER (-46..-16)
    MAX-ACCESS 	read-write
    STATUS 	current
    DESCRIPTION 	"Analog audio silence level in dBu."

    ::= { audioAnaDisp 7 }


audAnaSilenceTm OBJECT-TYPE
    SYNTAX 	INTEGER (0..60)
    MAX-ACCESS 	read-write
    STATUS 	current
    DESCRIPTION 	"Analog audio silence duration threshold (in seconds)."

    ::= { audioAnaDisp 8 }


audAnaProgLvl   OBJECT-TYPE
    SYNTAX 	INTEGER (-7..24)
    MAX-ACCESS 	read-write
    STATUS 	current
    DESCRIPTION 	"Analog audio peak program level in dBu"

    ::= { audioAnaDisp 9 }


audAnaTestLvl   OBJECT-TYPE
    SYNTAX 	INTEGER (-7..24)
    MAX-ACCESS 	read-write
    STATUS 	current
    DESCRIPTION 	"Analog audio test level in dBu"

    ::= { audioAnaDisp 10 }


audAnaCorrMtrSpd OBJECT-TYPE
    SYNTAX 	INTEGER (1..20)
    MAX-ACCESS 	read-write
    STATUS 	current
    DESCRIPTION 	"Analog audio correlation meter speed."

    ::= { audioAnaDisp 11 }


audAnaZeroDbMark OBJECT-TYPE
    SYNTAX 	INTEGER {
        dBu(0),
        peak-level(1),
        test-level(2)
    }
    MAX-ACCESS 	read-write
    STATUS 	current
    DESCRIPTION 	"Selects zero dB reference level for Analog audio."

    ::= { audioAnaDisp 12 }


audAnaMeterNum  OBJECT-TYPE
    SYNTAX 	INTEGER (0..5)
    MAX-ACCESS 	not-accessible
    STATUS 	current
    DESCRIPTION 	"Audio level meter number for Analog audio level meter table."

    ::= { audioAnaDisp 13 }


audAnaLevel     OBJECT-TYPE
    SYNTAX 	AudioLevel
    MAX-ACCESS 	read-only
    STATUS 	current
    DESCRIPTION 	"Current audio level of a analog audio input in dBu (x 100)"

    ::= { audAnaLvlEntry 1 }


audAnaSilenceCount OBJECT-TYPE
    SYNTAX 	INTEGER
    MAX-ACCESS 	read-only
    STATUS 	current
    DESCRIPTION 	"Number of analog silence events detected in the current session."

    ::= { audAnaLvlEntry 2 }


audAnaOverCount OBJECT-TYPE
    SYNTAX 	INTEGER
    MAX-ACCESS 	read-only
    STATUS 	current
    DESCRIPTION 	"Number of analog over events detected in the current session."

    ::= { audAnaLvlEntry 3 }


audAnaPeakLvl   OBJECT-TYPE
    SYNTAX 	AudioLevel
    MAX-ACCESS 	read-only
    STATUS 	current
    DESCRIPTION 	"Peak level in an Analog audio channel."

    ::= { audAnaLvlEntry 4 }


audAnaSessionPeak OBJECT-TYPE
    SYNTAX 	AudioLevel
    MAX-ACCESS 	read-only
    STATUS 	current
    DESCRIPTION 	"True peak signal level measured on the Analog audio channel."

    ::= { audAnaLvlEntry 5 }


audAnaSessionHighLvl OBJECT-TYPE
    SYNTAX 	AudioLevel
    MAX-ACCESS 	read-only
    STATUS 	current
    DESCRIPTION 	"The highest audio signal level measured by the signal level meters."

    ::= { audAnaLvlEntry 6 }


audAnaLeqAvg    OBJECT-TYPE
    SYNTAX 	AudioLevel
    MAX-ACCESS 	read-only
    STATUS 	current
    DESCRIPTION 	"10 second moving average Channel Loudness."

    ::= { audAnaLvlEntry 7 }


audAnaLeqSession OBJECT-TYPE
    SYNTAX 	AudioLevel
    MAX-ACCESS 	read-only
    STATUS 	current
    DESCRIPTION 	"Session controlled Channel Loudness, user defined averaging by session reset."

    ::= { audAnaLvlEntry 8 }


audAnaCurLoudness OBJECT-TYPE
    SYNTAX 	AudioLevel
    MAX-ACCESS 	read-only
    STATUS 	current
    DESCRIPTION 	"Immediate Channel Loudness, no averaging applied."

    ::= { audAnaLvlEntry 9 }


audAnaLeqPairAvg OBJECT-TYPE
    SYNTAX 	AudioLevel
    MAX-ACCESS 	read-only
    STATUS 	current
    DESCRIPTION 	"Average pair Loudness, 10 second moving average,note channel 1 and 2 (same pair), both report same value,same for 3&4 etc."

    ::= { audAnaLvlEntry 10 }


audAnaLeqPairSession OBJECT-TYPE
    SYNTAX 	AudioLevel
    MAX-ACCESS 	read-only
    STATUS 	current
    DESCRIPTION 	"Session pair Loudness, 10 second moving average,note channel 1 and 2 (same pair), both report same value,same for 3&4 etc."

    ::= { audAnaLvlEntry 11 }


audAnaPairCurLoudness OBJECT-TYPE
    SYNTAX 	AudioLevel
    MAX-ACCESS 	read-only
    STATUS 	current
    DESCRIPTION 	"Immediate pair Loudness, 10 second moving average,note channel 1 and 2 (same pair), both report same value,same for 3&4 etc."

    ::= { audAnaLvlEntry 12 }


audAnaLvlTable  OBJECT-TYPE
    SYNTAX 	SEQUENCE OF AudAnaLvlEntry
    MAX-ACCESS 	not-accessible
    STATUS 	current
    DESCRIPTION 	"Table of analog audio statistics for each audio channel that is associated with a level meter"

    ::= { audioAnaDisp 14 }


audAnaLvlEntry  OBJECT-TYPE
    SYNTAX 	AudAnaLvlEntry
    MAX-ACCESS 	not-accessible
    STATUS 	current
    DESCRIPTION 	"A row in the analog audio level table "
    INDEX { audAnaMeterNum }

    ::= { audAnaLvlTable 1 }


AudAnaLvlEntry ::= SEQUENCE {
    audAnaLevel 	AudioLevel,
    audAnaSilenceCount 	INTEGER,
    audAnaOverCount 	INTEGER,
    audAnaPeakLvl 	AudioLevel,
    audAnaSessionPeak 	AudioLevel,
    audAnaSessionHighLvl 	AudioLevel,
    audAnaLeqAvg 	AudioLevel,
    audAnaLeqSession 	AudioLevel,
    audAnaCurLoudness 	AudioLevel,
    audAnaLeqPairAvg 	AudioLevel,
    audAnaLeqPairSession 	AudioLevel,
    audAnaPairCurLoudness 	AudioLevel 
}

audAnaPkHoldSeg OBJECT-TYPE
    SYNTAX 	INTEGER {
        off(0),
        on(1)
    }
    MAX-ACCESS 	read-write
    STATUS 	current
    DESCRIPTION 	"Enable/disable analog audio peak held segment."

    ::= { audioAnaDisp 15 }


audAnaLvlMtrScale OBJECT-TYPE
    SYNTAX 	INTEGER {
        normal(0),
        custom(1)
    }
    MAX-ACCESS 	read-write
    STATUS 	current
    DESCRIPTION 	"On GET, indicates whether analog audio level meter scale isusing normal or custom values for height,offset and graticule step size. Setting the value to normal(0) resets analog audio meterscale parameters to normal values."

    ::= { audioAnaDisp 16 }


audAnaMeterType OBJECT-TYPE
    SYNTAX 	INTEGER {
        dbu(0),
        din(1),
        nordic(2),
        vu(3),
        ieee(4),
        bbc(5)
    }
    MAX-ACCESS 	read-write
    STATUS 	current
    DESCRIPTION 	"Analog audio meter presets for standard audio meter configurations."

    ::= { audioAnaDisp 17 }


audAnaLvlMtrHeight OBJECT-TYPE
    SYNTAX 	INTEGER (10..90)
    MAX-ACCESS 	read-write
    STATUS 	current
    DESCRIPTION 	"Range of scale for custom analog audio meter configuration in dB."

    ::= { audioAnaDisp 18 }


audAnaLvlMtrOffset OBJECT-TYPE
    SYNTAX 	INTEGER (-30..0)
    MAX-ACCESS 	read-write
    STATUS 	current
    DESCRIPTION 	"Top of scale for custom analog audio meter configuration in dBu."

    ::= { audioAnaDisp 19 }


audAnaGratStepSize OBJECT-TYPE
    SYNTAX 	INTEGER (3..10)
    MAX-ACCESS 	read-write
    STATUS 	current
    DESCRIPTION 	"Graticule step size for custom analog audio meter scale configuration in dB."

    ::= { audioAnaDisp 20 }


audAnaLissAGC   OBJECT-TYPE
    SYNTAX 	INTEGER {
        off(0),
        on(1)
    }
    MAX-ACCESS 	read-write
    STATUS 	current
    DESCRIPTION 	"Enable/disable lissajous automatic gain control for analog audio."

    ::= { audioAnaDisp 21 }


audAnaSessionCtrl OBJECT-TYPE
    SYNTAX 	INTEGER {
        reset(0),
        stop(1),
        run(2)
    }
    MAX-ACCESS 	read-write
    STATUS 	current
    DESCRIPTION 	"Audio sesssion control."

    ::= { audioAnaDisp 22 }


audAnaSessionRuntime OBJECT-TYPE
    SYNTAX 	DisplayString
    MAX-ACCESS 	read-only
    STATUS 	current
    DESCRIPTION 	"Audio session run time."

    ::= { audioAnaDisp 23 }


audAnaChanLoudThreshold OBJECT-TYPE
    SYNTAX 	INTEGER (-6..24)
    MAX-ACCESS 	read-write
    STATUS 	current
    DESCRIPTION 	"Analog Audio Channel Loudness threshold for Audio."

    ::= { audioAnaDisp 24 }


audAnaPgmLoudThreshold OBJECT-TYPE
    SYNTAX 	INTEGER (-6..24)
    MAX-ACCESS 	read-write
    STATUS 	current
    DESCRIPTION 	"Analog Audio Program Loudness threshold for Audio."

    ::= { audioAnaDisp 25 }


audAnaPhaseErrThr OBJECT-TYPE
    SYNTAX 	INTEGER (0..30)
    MAX-ACCESS 	read-write
    STATUS 	current
    DESCRIPTION 	"Analog audio correlation threshold for audio phase error in percent."

    ::= { audioAnaDisp 26 }


audAnaPhaseErrTime OBJECT-TYPE
    SYNTAX 	INTEGER (0..30)
    MAX-ACCESS 	read-write
    STATUS 	current
    DESCRIPTION 	"Analog audio phase error duration threshold (in seconds)."

    ::= { audioAnaDisp 27 }

-- 
-- display Group
-- Display control variables

currTile        OBJECT-TYPE
    SYNTAX 	INTEGER {
        tile1(0),
        tile2(1),
        tile3(2),
        tile4(3)
    }
    MAX-ACCESS 	not-accessible
    STATUS 	current
    DESCRIPTION 	"Currently Selected Tile. This is used as index in tables"

    ::= { display 1 }


gratIntensity   OBJECT-TYPE
    SYNTAX 	INTEGER (0..100)
    MAX-ACCESS 	read-write
    STATUS 	current
    DESCRIPTION 	"Graticule Intensity"

    ::= { display 2 }


rdOutIntensity  OBJECT-TYPE
    SYNTAX 	INTEGER (0..100)
    MAX-ACCESS 	read-write
    STATUS 	current
    DESCRIPTION 	"Readout Intensity"

    ::= { display 3 }


gratColor       OBJECT-TYPE
    SYNTAX 	INTEGER {
        gold(0),
        blue(1),
        red(2)
    }
    MAX-ACCESS 	read-write
    STATUS 	current
    DESCRIPTION 	"Graticule Color"

    ::= { display 4 }


rdOutColor      OBJECT-TYPE
    SYNTAX 	INTEGER {
        gold(0),
        blue(1),
        red(2)
    }
    MAX-ACCESS 	read-write
    STATUS 	current
    DESCRIPTION 	"Readout color"

    ::= { display 5 }


wfmColor        OBJECT-TYPE
    SYNTAX 	INTEGER {
        green(0),
        white(1),
        pseudo(2)
    }
    MAX-ACCESS 	read-write
    STATUS 	current
    DESCRIPTION 	"Waveform color"

    ::= { display 6 }


wfmIntensity    OBJECT-TYPE
    SYNTAX 	INTEGER (-50..50)
    MAX-ACCESS 	read-write
    STATUS 	current
    DESCRIPTION 	"Waveform Intensity"

    ::= { display 7 }


fullScreen      OBJECT-TYPE
    SYNTAX 	INTEGER {
        tile-none(0),
        tile-1(1),
        tile-2(2),
        tile-3(3),
        tile-4(4)
    }
    MAX-ACCESS 	read-write
    STATUS 	current
    DESCRIPTION 	"Select a tile to display it in full screen mode. (Select tile-none to display tiles in tile mode)"

    ::= { display 8 }


pictBrightness  OBJECT-TYPE
    SYNTAX 	INTEGER (-50..50)
    MAX-ACCESS 	read-write
    STATUS 	current
    DESCRIPTION 	"Picture brightness level"

    ::= { display 9 }


vgaOutput       OBJECT-TYPE
    SYNTAX 	INTEGER {
        normal(0),
        dim(1)
    }
    MAX-ACCESS 	read-write
    STATUS 	current
    DESCRIPTION 	"VGA brightness level"

    ::= { display 10 }


panelBacklight  OBJECT-TYPE
    SYNTAX 	INTEGER {
        off(0),
        on(1)
    }
    MAX-ACCESS 	read-write
    STATUS 	current
    DESCRIPTION 	"Front panel backlight enable"

    ::= { display 11 }


panelBklitIntensity OBJECT-TYPE
    SYNTAX 	INTEGER (1..10)
    MAX-ACCESS 	read-write
    STATUS 	current
    DESCRIPTION 	"Front panel backlight intensity level (1 - 10)"

    ::= { display 12 }


lcdBklitIntensity OBJECT-TYPE
    SYNTAX 	INTEGER (9..100)
    MAX-ACCESS 	read-write
    STATUS 	current
    DESCRIPTION 	"LCD backlight Intensity level (9-100)"

    ::= { display 13 }


pictBrtupRgbGamut OBJECT-TYPE
    SYNTAX 	INTEGER {
        off(0),
        on(1)
    }
    MAX-ACCESS 	read-write
    STATUS 	current
    DESCRIPTION 	"Picture bright up on RGB gamut error"

    ::= { display 14 }


pictBrtupCmpstGamut OBJECT-TYPE
    SYNTAX 	INTEGER {
        off(0),
        on(1)
    }
    MAX-ACCESS 	read-write
    STATUS 	current
    DESCRIPTION 	"Picture bright up on composite gamut error"

    ::= { display 15 }


pictRefreshMode OBJECT-TYPE
    SYNTAX 	INTEGER {
        crt(0),
        lcd(1),
        interlace(2)
    }
    MAX-ACCESS 	read-write
    STATUS 	current
    DESCRIPTION 	"Picture refresh mode"

    ::= { display 16 }


pictBrtupLumaGamut OBJECT-TYPE
    SYNTAX 	INTEGER {
        off(0),
        on(1)
    }
    MAX-ACCESS 	read-write
    STATUS 	current
    DESCRIPTION 	"Picture bright up on luma gamut error"

    ::= { display 17 }


freeze          OBJECT-TYPE
    SYNTAX 	INTEGER {
        off(0),
        on(1)
    }
    MAX-ACCESS 	read-write
    STATUS 	current
    DESCRIPTION 	"do the freeze in respective tiles this is a write-only trigger OID"

    ::= { freezeEntry 1 }


freezeDelete    OBJECT-TYPE
    SYNTAX 	INTEGER {
        off(0),
        on(1)
    }
    MAX-ACCESS 	read-write
    STATUS 	current
    DESCRIPTION 	"Delete the freeze in respective tiles this is a write-only trigger OID"

    ::= { freezeEntry 2 }


freezeDisplayMode OBJECT-TYPE
    SYNTAX 	INTEGER {
        live(0),
        frozen(1),
        both(2)
    }
    MAX-ACCESS 	read-write
    STATUS 	current
    DESCRIPTION 	"freeze Display Mode in selected Tile"

    ::= { freezeEntry 3 }


freezeTable     OBJECT-TYPE
    SYNTAX 	SEQUENCE OF FreezeEntry
    MAX-ACCESS 	not-accessible
    STATUS 	current
    DESCRIPTION 	"Table for freeze display modes"

    ::= { display 18 }


freezeEntry     OBJECT-TYPE
    SYNTAX 	FreezeEntry
    MAX-ACCESS 	not-accessible
    STATUS 	current
    DESCRIPTION 	"A row in the freeze Table"
    INDEX { currTile }

    ::= { freezeTable 1 }


FreezeEntry ::= SEQUENCE {
    freeze 	INTEGER,
    freezeDelete 	INTEGER,
    freezeDisplayMode 	INTEGER 
}

freezeMode      OBJECT-TYPE
    SYNTAX 	INTEGER {
        global(0),
        tile(1)
    }
    MAX-ACCESS 	read-write
    STATUS 	current
    DESCRIPTION 	"Sets Freeze behavior to Freeze all tiles (global 0) or the specified tile (tile 1)"

    ::= { display 19 }


vgaAspectRatio  OBJECT-TYPE
    SYNTAX 	INTEGER {
        normal(0),
        ratio16x9(1),
        ratio16x10(2)
    }
    MAX-ACCESS 	read-write
    STATUS 	current
    DESCRIPTION 	"Sets Vga aspect Ratio"

    ::= { display 20 }


displayThumbnail OBJECT-TYPE
    SYNTAX 	INTEGER {
        off(0),
        on(1)
    }
    MAX-ACCESS 	read-write
    STATUS 	current
    DESCRIPTION 	"display thumbnail picture"

    ::= { display 21 }


ccDisplayEnable OBJECT-TYPE
    SYNTAX 	INTEGER {
        disable(0),
        enable(1)
    }
    MAX-ACCESS 	read-write
    STATUS 	deprecated
    DESCRIPTION 	"Enable/Disable closed caption display"

    ::= { display 22 }


ccEnableSafePictArea OBJECT-TYPE
    SYNTAX 	INTEGER {
        disable(0),
        enable(1)
    }
    MAX-ACCESS 	read-write
    STATUS 	current
    DESCRIPTION 	"Enable/Disable safe picture area"

    ::= { display 23 }


pixMonOpColSpaceSD OBJECT-TYPE
    SYNTAX 	INTEGER {
        off(0),
        yCbCr(1),
        rgb(2)
    }
    MAX-ACCESS 	read-write
    STATUS 	current
    DESCRIPTION 	"Picture Monitor output color space for SD"

    ::= { display 24 }


pixMonOpColSpaceHD OBJECT-TYPE
    SYNTAX 	INTEGER {
        off(0),
        yCbCr(1),
        rgb(2)
    }
    MAX-ACCESS 	read-write
    STATUS 	current
    DESCRIPTION 	"Picture Monitor output color space for HD"

    ::= { display 25 }


vecIqAxis       OBJECT-TYPE
    SYNTAX 	INTEGER {
        off(0),
        on(1),
        onIfSD(2)
    }
    MAX-ACCESS 	read-write
    STATUS 	current
    DESCRIPTION 	"Display vector IQ axes (if on, IQ axes are displayed)"

    ::= { display 26 }


wfmGratUnits    OBJECT-TYPE
    SYNTAX 	INTEGER {
        auto(0),
        mV(1),
        ire(2),
        fullScalePct(3)
    }
    MAX-ACCESS 	read-write
    STATUS 	current
    DESCRIPTION 	"Selects the waveform graticule units"

    ::= { display 27 }


pictAspectRatio OBJECT-TYPE
    SYNTAX 	INTEGER {
        auto(0),
        ratio16x9(1)
    }
    MAX-ACCESS 	read-write
    STATUS 	current
    DESCRIPTION 	"Selects aspect ratio for picture display. Applies only to Composite and SD formats"

    ::= { display 28 }


pixMonOpCpst    OBJECT-TYPE
    SYNTAX 	INTEGER {
        off(0),
        on(1)
    }
    MAX-ACCESS 	read-write
    STATUS 	current
    DESCRIPTION 	"Enable/disable Picture Monitor output for composite"

    ::= { display 29 }


vecCompassRose  OBJECT-TYPE
    SYNTAX 	INTEGER {
        off(0),
        on(1)
    }
    MAX-ACCESS 	read-write
    STATUS 	current
    DESCRIPTION 	"Display vector compass rose graticule for SDI input signal"

    ::= { display 30 }


wfmVertArea     OBJECT-TYPE
    SYNTAX 	INTEGER {
        normal(0),
        maximum(1)
    }
    MAX-ACCESS 	read-write
    STATUS 	current
    DESCRIPTION 	"Selects waveform vertical area size for SDI input signals."

    ::= { display 31 }


sdiWfmGratUnits OBJECT-TYPE
    SYNTAX 	INTEGER {
        normal(0),
        percent(1)
    }
    MAX-ACCESS 	read-write
    STATUS 	current
    DESCRIPTION 	"Selects the waveform graticule units for SDI input signals"

    ::= { display 32 }


fieldSweepCursorLine OBJECT-TYPE
    SYNTAX 	INTEGER {
        off(0),
        on(1)
    }
    MAX-ACCESS 	read-write
    STATUS 	current
    DESCRIPTION 	"Display field sweep line select cursor in line select mode."

    ::= { display 33 }


sdiOutput       OBJECT-TYPE
    SYNTAX 	INTEGER {
        pixmon(0),
        loopout-follows-input(1),
        other(2)
    }
    MAX-ACCESS 	read-write
    STATUS 	deprecated
    DESCRIPTION 	"Select SDI output as pixmon or SDI loopout or other."

    ::= { display 34 }


pixMonLinkSelect OBJECT-TYPE
    SYNTAX 	INTEGER {
        links-combined(0),
        link-a(1),
        link-b(2)
    }
    MAX-ACCESS 	read-write
    STATUS 	deprecated
    DESCRIPTION 	"Link selection for pixmon output in dual-link input"

    ::= { display 35 }


pixMonChanSelect OBJECT-TYPE
    SYNTAX 	INTEGER {
        chan1(0),
        chan2(1)
    }
    MAX-ACCESS 	read-write
    STATUS 	current
    DESCRIPTION 	"Channel selection for pixmon output in simultaneous input mode"

    ::= { display 36 }


selectTile      OBJECT-TYPE
    SYNTAX 	INTEGER {
        tile1(1),
        tile2(2),
        tile3(3),
        tile4(4)
    }
    MAX-ACCESS 	read-write
    STATUS 	current
    DESCRIPTION 	"Select the active tile."

    ::= { display 37 }


t3gTestSignal   OBJECT-TYPE
    SYNTAX 	INTEGER {
        color-bar-100(0),
        color-bar-75(1),
        pathogenic-signal(2)
    }
    MAX-ACCESS 	read-write
    STATUS 	deprecated
    DESCRIPTION 	"Select the pattern of 3G test signal to be generated."

    ::= { display 38 }


t3gTestSignalLvl OBJECT-TYPE
    SYNTAX 	INTEGER {
        level-A(0),
        level-B(1)
    }
    MAX-ACCESS 	read-write
    STATUS 	deprecated
    DESCRIPTION 	"Select the level of 3G test signal to be generated."

    ::= { display 39 }


t3gTestSignalFmt OBJECT-TYPE
    SYNTAX 	INTEGER {
        std-1080p-50(0),
        std-1080p-59-94(1),
        std-1080p-60(2)
    }
    MAX-ACCESS 	read-write
    STATUS 	deprecated
    DESCRIPTION 	"Select the format of 3G test signal to be generated."

    ::= { display 40 }


captureType     OBJECT-TYPE
    SYNTAX 	INTEGER {
        freeze(0),
        buffer(1)
    }
    MAX-ACCESS 	read-write
    STATUS 	current
    DESCRIPTION 	"Select the capture type - freeze mode or buffer mode."

    ::= { display 41 }


captureFrame    OBJECT-TYPE
    SYNTAX 	BITS {
        channel-1(0),
        channel-2(1)
    }
    MAX-ACCESS 	read-write
    STATUS 	current
    DESCRIPTION 	"On write, capture a frame of video from SDI inputs on selected monitoring channel. On read, indicates channels with valid capture buffer data."

    ::= { display 42 }


captureDelete   OBJECT-TYPE
    SYNTAX 	BITS {
        channel-1(0),
        channel-2(1)
    }
    MAX-ACCESS 	read-write
    STATUS 	current
    DESCRIPTION 	"Delete the captured buffer for selected monitoring channel (write-only)."

    ::= { display 43 }


captureTrigger  OBJECT-TYPE
    SYNTAX 	INTEGER {
        stop(0),
        run(1)
    }
    MAX-ACCESS 	read-write
    STATUS 	current
    DESCRIPTION 	"Enable or disable automatic triggers for capture on errors. Automatic triggers must be disabled for manual capture."

    ::= { display 44 }


captureTriggerEvents OBJECT-TYPE
    SYNTAX 	BITS {
        eav-error(0),
        sav-error(1),
        hd-line-number-error(2),
        hd-ycrc-error(3),
        hd-ccrc-error(4),
        hd-yanc-csum-error(5),
        hd-canc-csum-error(6),
        sd-ap-crc-error(7),
        sd-ff-crc-error(8),
        luma-gamut-error(9),
        cmpst-gamut-error(10),
        rgb-gamut-error(11)
    }
    MAX-ACCESS 	read-write
    STATUS 	current
    DESCRIPTION 	"Select alarms that trigger buffer capture (when automatic trigger is enabled)."

    ::= { display 45 }


sdiTestSignalPattern OBJECT-TYPE
    SYNTAX 	INTEGER {
        color-bar-100(0),
        color-bar-75(1),
        pathological-signal(2)
    }
    MAX-ACCESS 	read-write
    STATUS 	deprecated
    DESCRIPTION 	"Select the pattern of SDI test signal to be generated."

    ::= { display 46 }


sdiTestSignalFmt OBJECT-TYPE
    SYNTAX 	INTEGER {
        std-525i-59-94(0),
        std-625i-50(1),
        std-1080i-50(2),
        std-1080i-59-94(3),
        std-1080i-60(4),
        std-1080p-50(5),
        std-1080p-59-94(6),
        std-1080p-60(7)
    }
    MAX-ACCESS 	read-write
    STATUS 	deprecated
    DESCRIPTION 	"Select the format of SDI test signal to be generated."

    ::= { display 47 }


traceOverlay    OBJECT-TYPE
    SYNTAX 	INTEGER {
        none(0),
        wfm-vec(1)
    }
    MAX-ACCESS 	read-write
    STATUS 	current
    DESCRIPTION 	"Allowd trace overlay of waveform and vector"

    ::= { display 49 }


infPersist      OBJECT-TYPE
    SYNTAX 	INTEGER {
        off(0),
        on(1)
    }
    MAX-ACCESS 	read-write
    STATUS 	current
    DESCRIPTION 	"Turns off/on infinite persistance"

    ::= { persistEntry 1 }


persistTable    OBJECT-TYPE
    SYNTAX 	SEQUENCE OF PersistEntry
    MAX-ACCESS 	not-accessible
    STATUS 	current
    DESCRIPTION 	"Table for infinite display"

    ::= { display 50 }


persistEntry    OBJECT-TYPE
    SYNTAX 	PersistEntry
    MAX-ACCESS 	not-accessible
    STATUS 	current
    DESCRIPTION 	"A row in the persist Table"
    INDEX { currTile }

    ::= { persistTable 1 }


PersistEntry ::= SEQUENCE {
    infPersist 	INTEGER 
}

hdmiOutHdcpStatus OBJECT-TYPE
    SYNTAX 	INTEGER {
        disabled(0),
        connecting(1),
        enabled(2),
        updated(3)
    }
    MAX-ACCESS 	read-only
    STATUS 	current
    DESCRIPTION 	"HDMI Output HDCP Negotiation State"

    ::= { display 51 }

-- 
-- comp Group
-- Composite Input variables

compDcRestore   OBJECT-TYPE
    SYNTAX 	INTEGER {
        off(0),
        slow(1),
        fast(2)
    }
    MAX-ACCESS 	read-write
    STATUS 	current
    DESCRIPTION 	"DC Restore function of composite input"

    ::= { comp 1 }


compPalVector   OBJECT-TYPE
    SYNTAX 	INTEGER {
        normal(0),
        plusV(1)
    }
    MAX-ACCESS 	read-write
    STATUS 	current
    DESCRIPTION 	"PAL Vector mode of composite input"

    ::= { comp 2 }


compNtscSetup   OBJECT-TYPE
    SYNTAX 	INTEGER {
        off(0),
        on(1)
    }
    MAX-ACCESS 	read-write
    STATUS 	current
    DESCRIPTION 	"NTSC setup of composite input"

    ::= { comp 3 }


compSyncLockMode OBJECT-TYPE
    SYNTAX 	INTEGER {
        direct(0),
        afc(1)
    }
    MAX-ACCESS 	read-write
    STATUS 	current
    DESCRIPTION 	"Composite input sync lock mode,direct = fast and afc = slow"

    ::= { comp 4 }


refSyncLockMode OBJECT-TYPE
    SYNTAX 	INTEGER {
        direct(0),
        afc(1)
    }
    MAX-ACCESS 	not-accessible
    STATUS 	deprecated
    DESCRIPTION 	"External reference sync lock, direct = fast and afc = slow"

    ::= { comp 5 }

-- 
-- cableMeter group
-- OIDs for cable meter

cableType       OBJECT-TYPE
    SYNTAX 	INTEGER {
        belden-8281(0),
        belden-1694A(1),
        belden-1505(2),
        belden-1855A(4),
        canare-L-5CFB(5),
        image-1000(6)
    }
    MAX-ACCESS 	read-write
    STATUS 	current
    DESCRIPTION 	"Sets the cable type for the cable meter"

    ::= { cableMeter 1 }


cableLoss       OBJECT-TYPE
    SYNTAX 	DBLevel
    MAX-ACCESS 	read-only
    STATUS 	current
    DESCRIPTION 	"Measured cable loss"

    ::= { cableMeter 2 }


approxCableLen  OBJECT-TYPE
    SYNTAX 	INTEGER
    MAX-ACCESS 	read-only
    STATUS 	current
    DESCRIPTION 	"Measured Cable Length in meters of equivalent length of cable, type specified by the cableType setting"

    ::= { cableMeter 3 }


sourceLevel     OBJECT-TYPE
    SYNTAX 	INTEGER
    MAX-ACCESS 	read-only
    STATUS 	current
    DESCRIPTION 	"Source level % nominal (800mV)"

    ::= { cableMeter 4 }


srcLevelMaxLimit OBJECT-TYPE
    SYNTAX 	INTEGER (600..1000)
    MAX-ACCESS 	read-write
    STATUS 	current
    DESCRIPTION 	"Sets the upper threshold for the srcLevelTrap and srcLevelAlarm."

    ::= { cableMeter 5 }


srcLevelMinLimit OBJECT-TYPE
    SYNTAX 	INTEGER (600..1000)
    MAX-ACCESS 	read-write
    STATUS 	current
    DESCRIPTION 	"Sets the lower threshold for the srcLevelTrap and srcLevelAlarm"

    ::= { cableMeter 6 }


cableLossLimitSd OBJECT-TYPE
    SYNTAX 	DBLevel
    MAX-ACCESS 	read-write
    STATUS 	current
    DESCRIPTION 	"Sets the threshold for the cable loss alarm for SD signals"

    ::= { cableMeter 7 }


cableLossLimitHd OBJECT-TYPE
    SYNTAX 	DBLevel
    MAX-ACCESS 	read-write
    STATUS 	current
    DESCRIPTION 	"Sets the threshold for the cable loss alarm for HD signals"

    ::= { cableMeter 8 }


cableLengthLimitSd OBJECT-TYPE
    SYNTAX 	INTEGER (0..300)
    MAX-ACCESS 	read-write
    STATUS 	current
    DESCRIPTION 	"Sets the threshold for the cable length alarm for SD signals"

    ::= { cableMeter 9 }


cableLengthLimitHd OBJECT-TYPE
    SYNTAX 	INTEGER (0..300)
    MAX-ACCESS 	read-write
    STATUS 	current
    DESCRIPTION 	"Sets the threshold for the cable length alarm for HD signals"

    ::= { cableMeter 10 }


cableLossLimit3G OBJECT-TYPE
    SYNTAX 	DBLevel (0..3000)
    MAX-ACCESS 	read-write
    STATUS 	current
    DESCRIPTION 	"Sets the threshold for the cable loss alarm for 3G signals"

    ::= { cableMeter 11 }


cableLengthLimit3G OBJECT-TYPE
    SYNTAX 	INTEGER (0..300)
    MAX-ACCESS 	read-write
    STATUS 	current
    DESCRIPTION 	"Sets the threshold for the cable length alarm for 3G signals"

    ::= { cableMeter 12 }

-- 
-- anc Group
-- Ancillary Data mode variables

ancDID          OBJECT-TYPE
    SYNTAX 	INTEGER (1..255)
    MAX-ACCESS 	read-write
    STATUS 	deprecated
    DESCRIPTION 	"anc data ID (DID)."

    ::= { ancEntry 1 }


ancSDID         OBJECT-TYPE
    SYNTAX 	INTEGER (0..255)
    MAX-ACCESS 	read-write
    STATUS 	deprecated
    DESCRIPTION 	"anc secondary data ID (SDID)."

    ::= { ancEntry 2 }


ancViewMode     OBJECT-TYPE
    SYNTAX 	INTEGER {
        watchlist(0),
        all(1)
    }
    MAX-ACCESS 	read-write
    STATUS 	current
    DESCRIPTION 	"View Mode in the ANC Data Inspector Display"

    ::= { ancEntry 3 }


ancAllSessionsReset OBJECT-TYPE
    SYNTAX 	INTEGER
    MAX-ACCESS 	read-write
    STATUS 	current
    DESCRIPTION 	"Causes the Global session reset of ANC Data Inspector display(write only)"

    ::= { ancEntry 4 }


ancTable        OBJECT-TYPE
    SYNTAX 	SEQUENCE OF AncEntry
    MAX-ACCESS 	not-accessible
    STATUS 	current
    DESCRIPTION 	"Table for ancillary data display mode"

    ::= { anc 1 }


ancEntry        OBJECT-TYPE
    SYNTAX 	AncEntry
    MAX-ACCESS 	not-accessible
    STATUS 	current
    DESCRIPTION 	"a row in the ancillary data table"
    INDEX { currTile }

    ::= { ancTable 1 }


AncEntry ::= SEQUENCE {
    ancDID 	INTEGER,
    ancSDID 	INTEGER,
    ancViewMode 	INTEGER,
    ancAllSessionsReset 	INTEGER 
}

ancUserTypes    OBJECT-TYPE
    SYNTAX 	INTEGER (0..7)
    MAX-ACCESS 	not-accessible
    STATUS 	current
    DESCRIPTION 	"User Type Number"

    ::= { anc 2 }


ancUserTypeName OBJECT-TYPE
    SYNTAX 	DisplayString
    MAX-ACCESS 	read-write
    STATUS 	current
    DESCRIPTION 	"anc data type name"

    ::= { ancUserTypeEntry 1 }


ancUserTypeDID  OBJECT-TYPE
    SYNTAX 	INTEGER (1..255)
    MAX-ACCESS 	read-write
    STATUS 	current
    DESCRIPTION 	"anc data ID (DID).User Type Config"

    ::= { ancUserTypeEntry 2 }


ancUserTypeSDID OBJECT-TYPE
    SYNTAX 	INTEGER (0..255)
    MAX-ACCESS 	read-write
    STATUS 	current
    DESCRIPTION 	"anc secondary data ID (SDID).User Type Config"

    ::= { ancUserTypeEntry 3 }


ancUserTypeTable OBJECT-TYPE
    SYNTAX 	SEQUENCE OF AncUserTypeEntry
    MAX-ACCESS 	not-accessible
    STATUS 	current
    DESCRIPTION 	"Table for ancillary data display User Type Config"

    ::= { anc 3 }


ancUserTypeEntry OBJECT-TYPE
    SYNTAX 	AncUserTypeEntry
    MAX-ACCESS 	not-accessible
    STATUS 	current
    DESCRIPTION 	"a row in the ancillary data User Type Config"
    INDEX { ancUserTypes }

    ::= { ancUserTypeTable 1 }


AncUserTypeEntry ::= SEQUENCE {
    ancUserTypeName 	DisplayString,
    ancUserTypeDID 	INTEGER,
    ancUserTypeSDID 	INTEGER 
}

ancWatchRP165EDH OBJECT-TYPE
    SYNTAX 	INTEGER {
        off(0),
        on(1)
    }
    MAX-ACCESS 	read-write
    STATUS 	current
    DESCRIPTION 	"Enable or Disable RP165EDH from Config Watch List "

    ::= { anc 4 }


ancWatchS352mVPID OBJECT-TYPE
    SYNTAX 	INTEGER {
        off(0),
        on(1)
    }
    MAX-ACCESS 	read-write
    STATUS 	current
    DESCRIPTION 	"Enable or Disable S352mVPID from Config Watch List "

    ::= { anc 5 }


ancWatchS353mMPEGv OBJECT-TYPE
    SYNTAX 	INTEGER {
        off(0),
        on(1)
    }
    MAX-ACCESS 	read-write
    STATUS 	current
    DESCRIPTION 	"Enable or Disable S353mMPEGv from Config Watch List "

    ::= { anc 6 }


ancWatchS353mMPEGh OBJECT-TYPE
    SYNTAX 	INTEGER {
        off(0),
        on(1)
    }
    MAX-ACCESS 	read-write
    STATUS 	current
    DESCRIPTION 	"Enable or Disable S353mMPEGh from Config Watch List "

    ::= { anc 7 }


ancWatchRP214KLVv OBJECT-TYPE
    SYNTAX 	INTEGER {
        off(0),
        on(1)
    }
    MAX-ACCESS 	read-write
    STATUS 	current
    DESCRIPTION 	"Enable or Disable RP214KLVv from Config Watch List "

    ::= { anc 8 }


ancWatchRP214KLVh OBJECT-TYPE
    SYNTAX 	INTEGER {
        off(0),
        on(1)
    }
    MAX-ACCESS 	read-write
    STATUS 	current
    DESCRIPTION 	"Enable or Disable RP214KLVh from Config Watch List "

    ::= { anc 9 }


ancWatchRP223UMID OBJECT-TYPE
    SYNTAX 	INTEGER {
        off(0),
        on(1)
    }
    MAX-ACCESS 	read-write
    STATUS 	current
    DESCRIPTION 	"Enable or Disable RP223UMID from Config Watch List "

    ::= { anc 10 }


ancWatchRP215FilmXfer OBJECT-TYPE
    SYNTAX 	INTEGER {
        off(0),
        on(1)
    }
    MAX-ACCESS 	read-write
    STATUS 	current
    DESCRIPTION 	"Enable or Disable RP215FilmXfer from Config Watch List "

    ::= { anc 11 }


ancWatchS305mSD-SDTI OBJECT-TYPE
    SYNTAX 	INTEGER {
        off(0),
        on(1)
    }
    MAX-ACCESS 	read-write
    STATUS 	current
    DESCRIPTION 	"Enable or Disable S305mSD-SDTI from Config Watch List "

    ::= { anc 12 }


ancWatchS348mHD-SDTI OBJECT-TYPE
    SYNTAX 	INTEGER {
        off(0),
        on(1)
    }
    MAX-ACCESS 	read-write
    STATUS 	current
    DESCRIPTION 	"Enable or Disable S348mHD-SDTI from Config Watch List "

    ::= { anc 13 }


ancWatchS299mCtrl OBJECT-TYPE
    SYNTAX 	INTEGER {
        off(0),
        on(1)
    }
    MAX-ACCESS 	read-write
    STATUS 	current
    DESCRIPTION 	"Enable or Disable S299mCtrl from Config Watch List "

    ::= { anc 14 }


ancWatchS299mAudio OBJECT-TYPE
    SYNTAX 	INTEGER {
        off(0),
        on(1)
    }
    MAX-ACCESS 	read-write
    STATUS 	current
    DESCRIPTION 	"Enable or Disable S299mAudio from Config Watch List "

    ::= { anc 15 }


ancWatchS272mCtrl OBJECT-TYPE
    SYNTAX 	INTEGER {
        off(0),
        on(1)
    }
    MAX-ACCESS 	read-write
    STATUS 	current
    DESCRIPTION 	"Enable or Disable S272mCtrl from Config Watch List "

    ::= { anc 16 }


ancWatchS272mAudio OBJECT-TYPE
    SYNTAX 	INTEGER {
        off(0),
        on(1)
    }
    MAX-ACCESS 	read-write
    STATUS 	current
    DESCRIPTION 	"Enable or Disable S272mAudio from Config Watch List "

    ::= { anc 17 }


ancWatchS272mExt OBJECT-TYPE
    SYNTAX 	INTEGER {
        off(0),
        on(1)
    }
    MAX-ACCESS 	read-write
    STATUS 	current
    DESCRIPTION 	"Enable or Disable S272mExt from Config Watch List "

    ::= { anc 18 }


ancWatchS334-1CDP708 OBJECT-TYPE
    SYNTAX 	INTEGER {
        off(0),
        on(1)
    }
    MAX-ACCESS 	read-write
    STATUS 	current
    DESCRIPTION 	"Enable or Disable S334-1CDP708 from Config Watch List "

    ::= { anc 19 }


ancWatchS334-1EIA608 OBJECT-TYPE
    SYNTAX 	INTEGER {
        off(0),
        on(1)
    }
    MAX-ACCESS 	read-write
    STATUS 	current
    DESCRIPTION 	"Enable or Disable S334-1EIA608 from Config Watch List "

    ::= { anc 20 }


ancWatchS334-1Teletext OBJECT-TYPE
    SYNTAX 	INTEGER {
        off(0),
        on(1)
    }
    MAX-ACCESS 	read-write
    STATUS 	current
    DESCRIPTION 	"Enable or Disable S334-1Teletext from Config Watch List "

    ::= { anc 21 }


ancWatchS334SDE OBJECT-TYPE
    SYNTAX 	INTEGER {
        off(0),
        on(1)
    }
    MAX-ACCESS 	read-write
    STATUS 	current
    DESCRIPTION 	"Enable or Disable S334SDE from Config Watch List "

    ::= { anc 22 }


ancWatchAribB37HD OBJECT-TYPE
    SYNTAX 	INTEGER {
        off(0),
        on(1)
    }
    MAX-ACCESS 	read-write
    STATUS 	current
    DESCRIPTION 	"Enable or Disable AribB37HD from Config Watch List "

    ::= { anc 23 }


ancWatchAribB37SD OBJECT-TYPE
    SYNTAX 	INTEGER {
        off(0),
        on(1)
    }
    MAX-ACCESS 	read-write
    STATUS 	current
    DESCRIPTION 	"Enable or Disable AribB37SD from Config Watch List "

    ::= { anc 24 }


ancWatchAribB37Mob OBJECT-TYPE
    SYNTAX 	INTEGER {
        off(0),
        on(1)
    }
    MAX-ACCESS 	read-write
    STATUS 	current
    DESCRIPTION 	"Enable or Disable AribB37Mob from Config Watch List "

    ::= { anc 25 }


ancWatchAribB37Ana OBJECT-TYPE
    SYNTAX 	INTEGER {
        off(0),
        on(1)
    }
    MAX-ACCESS 	read-write
    STATUS 	current
    DESCRIPTION 	"Enable or Disable AribB37Ana from Config Watch List "

    ::= { anc 26 }


ancWatchAribB27CC OBJECT-TYPE
    SYNTAX 	INTEGER {
        off(0),
        on(1)
    }
    MAX-ACCESS 	read-write
    STATUS 	current
    DESCRIPTION 	"Enable or Disable AribB27CC from Config Watch List "

    ::= { anc 27 }


ancWatchRDD8Op47Sdp OBJECT-TYPE
    SYNTAX 	INTEGER {
        off(0),
        on(1)
    }
    MAX-ACCESS 	read-write
    STATUS 	current
    DESCRIPTION 	"Enable or Disable RDD8Op47Sdp from Config Watch List "

    ::= { anc 28 }


ancWatchRDD8Op47Multi OBJECT-TYPE
    SYNTAX 	INTEGER {
        off(0),
        on(1)
    }
    MAX-ACCESS 	read-write
    STATUS 	current
    DESCRIPTION 	"Enable or Disable RDD8Op47Multi from Config Watch List "

    ::= { anc 29 }


ancWatchAribB35 OBJECT-TYPE
    SYNTAX 	INTEGER {
        off(0),
        on(1)
    }
    MAX-ACCESS 	read-write
    STATUS 	current
    DESCRIPTION 	"Enable or Disable AribB35 from Config Watch List "

    ::= { anc 30 }


ancWatchAribB39 OBJECT-TYPE
    SYNTAX 	INTEGER {
        off(0),
        on(1)
    }
    MAX-ACCESS 	read-write
    STATUS 	current
    DESCRIPTION 	"Enable or Disable AribB39 from Config Watch List "

    ::= { anc 31 }


ancWatchITUR-BT1685 OBJECT-TYPE
    SYNTAX 	INTEGER {
        off(0),
        on(1)
    }
    MAX-ACCESS 	read-write
    STATUS 	current
    DESCRIPTION 	"Enable or Disable ITUR-BT1685 from Config Watch List "

    ::= { anc 32 }


ancWatchAribTr-B22 OBJECT-TYPE
    SYNTAX 	INTEGER {
        off(0),
        on(1)
    }
    MAX-ACCESS 	read-write
    STATUS 	current
    DESCRIPTION 	"Enable or Disable AribTr-B22 from Config Watch List "

    ::= { anc 33 }


ancWatchAribTr-B23-1 OBJECT-TYPE
    SYNTAX 	INTEGER {
        off(0),
        on(1)
    }
    MAX-ACCESS 	read-write
    STATUS 	current
    DESCRIPTION 	"Enable or Disable AribTr-B23-1 from Config Watch List "

    ::= { anc 34 }


ancWatchAribTr-B23-2 OBJECT-TYPE
    SYNTAX 	INTEGER {
        off(0),
        on(1)
    }
    MAX-ACCESS 	read-write
    STATUS 	current
    DESCRIPTION 	"Enable or Disable AribTr-B23-2 from Config Watch List "

    ::= { anc 35 }


ancWatchS334RP207 OBJECT-TYPE
    SYNTAX 	INTEGER {
        off(0),
        on(1)
    }
    MAX-ACCESS 	read-write
    STATUS 	current
    DESCRIPTION 	"Enable or Disable S334RP207 from Config Watch List "

    ::= { anc 36 }


ancWatchS334RP208 OBJECT-TYPE
    SYNTAX 	INTEGER {
        off(0),
        on(1)
    }
    MAX-ACCESS 	read-write
    STATUS 	current
    DESCRIPTION 	"Enable or Disable S334RP208 from Config Watch List "

    ::= { anc 37 }


ancWatchRP188   OBJECT-TYPE
    SYNTAX 	INTEGER {
        off(0),
        on(1)
    }
    MAX-ACCESS 	read-write
    STATUS 	current
    DESCRIPTION 	"Enable or Disable ST12.2 (RP188) from Config Watch List "

    ::= { anc 38 }


ancWatchRP196LTC OBJECT-TYPE
    SYNTAX 	INTEGER {
        off(0),
        on(1)
    }
    MAX-ACCESS 	read-write
    STATUS 	current
    DESCRIPTION 	"Enable or Disable RP196LTC from Config Watch List "

    ::= { anc 39 }


ancWatchRP196VITC OBJECT-TYPE
    SYNTAX 	INTEGER {
        off(0),
        on(1)
    }
    MAX-ACCESS 	read-write
    STATUS 	current
    DESCRIPTION 	"Enable or Disable RP196VITC from Config Watch List "

    ::= { anc 40 }


ancWatchLinkCrypto OBJECT-TYPE
    SYNTAX 	INTEGER {
        off(0),
        on(1)
    }
    MAX-ACCESS 	read-write
    STATUS 	current
    DESCRIPTION 	"Enable or Disable LinkCrypto from Config Watch List "

    ::= { anc 41 }


ancWatchS346M   OBJECT-TYPE
    SYNTAX 	INTEGER {
        off(0),
        on(1)
    }
    MAX-ACCESS 	read-write
    STATUS 	current
    DESCRIPTION 	"Enable or Disable S346M from Config Watch List "

    ::= { anc 42 }


ancWatchS2016-3AFD-Bar OBJECT-TYPE
    SYNTAX 	INTEGER {
        off(0),
        on(1)
    }
    MAX-ACCESS 	read-write
    STATUS 	current
    DESCRIPTION 	"Enable or Disable S2016-3AFD-Bar from Config Watch List "

    ::= { anc 43 }


ancWatchS2016-3PanScan OBJECT-TYPE
    SYNTAX 	INTEGER {
        off(0),
        on(1)
    }
    MAX-ACCESS 	read-write
    STATUS 	current
    DESCRIPTION 	"Enable or Disable S2016-3PanScan from Config Watch List "

    ::= { anc 44 }


ancWatchS334-1Future OBJECT-TYPE
    SYNTAX 	INTEGER {
        off(0),
        on(1)
    }
    MAX-ACCESS 	read-write
    STATUS 	current
    DESCRIPTION 	"Enable or Disable S334-1Future from Config Watch List "

    ::= { anc 45 }


ancWatchRP2010Scte104 OBJECT-TYPE
    SYNTAX 	INTEGER {
        off(0),
        on(1)
    }
    MAX-ACCESS 	read-write
    STATUS 	current
    DESCRIPTION 	"Enable or Disable RP2010Scte104 from Config Watch List "

    ::= { anc 46 }


ancWatchRP2031ScteVBI OBJECT-TYPE
    SYNTAX 	INTEGER {
        off(0),
        on(1)
    }
    MAX-ACCESS 	read-write
    STATUS 	current
    DESCRIPTION 	"Enable or Disable RP2031ScteVBI from Config Watch List "

    ::= { anc 47 }


ancWatchRP2020Meta OBJECT-TYPE
    SYNTAX 	INTEGER {
        off(0),
        on(1)
    }
    MAX-ACCESS 	read-write
    STATUS 	current
    DESCRIPTION 	"Enable or Disable RP2020Meta from Config Watch List "

    ::= { anc 48 }


ancWatchUserTypes OBJECT-TYPE
    SYNTAX 	INTEGER {
        off(0),
        on(1)
    }
    MAX-ACCESS 	read-write
    STATUS 	current
    DESCRIPTION 	"Enable or Disable UserTypes from Config Watch List "

    ::= { anc 49 }


ancWatchSelectAll OBJECT-TYPE
    SYNTAX 	INTEGER {
        ready(0),
        select(1)
    }
    MAX-ACCESS 	read-write
    STATUS 	current
    DESCRIPTION 	"Select all the anc types in Config Watch List (write-only). "

    ::= { anc 50 }


ancWatchClearAll OBJECT-TYPE
    SYNTAX 	INTEGER {
        ready(0),
        clear(1)
    }
    MAX-ACCESS 	read-write
    STATUS 	current
    DESCRIPTION 	"Clear all the anc types in Config Watch List (write-only). "

    ::= { anc 51 }


ancWatchResetToDefault OBJECT-TYPE
    SYNTAX 	INTEGER {
        ready(0),
        reset(1)
    }
    MAX-ACCESS 	read-write
    STATUS 	current
    DESCRIPTION 	"Reset all the anc types to default state in Config Watch List (write-only). "

    ::= { anc 52 }

-- 
-- datalist Group
-- Datalist display mode variables

dataTraceType   OBJECT-TYPE
    SYNTAX 	INTEGER {
        video(0),
        data(1)
    }
    MAX-ACCESS 	read-write
    STATUS 	current
    DESCRIPTION 	"Datalist colorspace."

    ::= { datalistEntry 1 }


dataChannelSelect OBJECT-TYPE
    SYNTAX 	DisplayString
    MAX-ACCESS 	read-write
    STATUS 	current
    DESCRIPTION 	"Datalist display color-space components (Y Cb Cr or R G B or X Y Z). For dual link input, A(alpha trace) is also allowed."

    ::= { datalistEntry 2 }


dataReadoutFmt  OBJECT-TYPE
    SYNTAX 	INTEGER {
        hex(0),
        decimal(1),
        binary(2)
    }
    MAX-ACCESS 	read-write
    STATUS 	current
    DESCRIPTION 	"Datalist readout format."

    ::= { datalistEntry 3 }


dataLinkSelect  OBJECT-TYPE
    SYNTAX 	INTEGER {
        link-a(0),
        link-b(1),
        dual-link(2)
    }
    MAX-ACCESS 	read-write
    STATUS 	current
    DESCRIPTION 	"Datalist link selection."

    ::= { datalistEntry 4 }


datalistTable   OBJECT-TYPE
    SYNTAX 	SEQUENCE OF DatalistEntry
    MAX-ACCESS 	not-accessible
    STATUS 	current
    DESCRIPTION 	"Table for datalist data display mode"

    ::= { datalist 1 }


datalistEntry   OBJECT-TYPE
    SYNTAX 	DatalistEntry
    MAX-ACCESS 	not-accessible
    STATUS 	current
    DESCRIPTION 	"a row in the datalist data table"
    INDEX { currTile }

    ::= { datalistTable 1 }


DatalistEntry ::= SEQUENCE {
    dataTraceType 	INTEGER,
    dataChannelSelect 	DisplayString,
    dataReadoutFmt 	INTEGER,
    dataLinkSelect 	INTEGER 
}
-- 
-- bowtie group
-- Waveform display mode variables

bowtieMode      OBJECT-TYPE
    SYNTAX 	INTEGER {
        parade(0),
        overlay(1)
    }
    MAX-ACCESS 	read-write
    STATUS 	current
    DESCRIPTION 	"Bowtie sweep display mode."

    ::= { bowtieEntry 1 }


bowtieSweepMode OBJECT-TYPE
    SYNTAX 	INTEGER {
        h1(1),
        f1(3)
    }
    MAX-ACCESS 	read-write
    STATUS 	current
    DESCRIPTION 	"Bowtie sweep mode and timbase"

    ::= { bowtieEntry 2 }


bowtieGain      OBJECT-TYPE
    SYNTAX 	INTEGER {
        gain-x1(0),
        gain-x5(1),
        gain-x10(2),
        gain-x2(3)
    }
    MAX-ACCESS 	read-write
    STATUS 	current
    DESCRIPTION 	"Bowtie fixed gain values"

    ::= { bowtieEntry 3 }


bowtieVarGainEnable OBJECT-TYPE
    SYNTAX 	INTEGER {
        off(0),
        on(1)
    }
    MAX-ACCESS 	read-write
    STATUS 	current
    DESCRIPTION 	"Enable/diable bowtie variable gain"

    ::= { bowtieEntry 4 }


bowtieVarGain   OBJECT-TYPE
    SYNTAX 	DisplayString
    MAX-ACCESS 	read-write
    STATUS 	current
    DESCRIPTION 	"Bowtie variable gain values (effective). Range of values depends on current value of bowtieGain."

    ::= { bowtieEntry 5 }


bowtieCursorMode OBJECT-TYPE
    SYNTAX 	INTEGER {
        volt(0),
        time(1),
        voltAndTime(2)
    }
    MAX-ACCESS 	read-write
    STATUS 	current
    DESCRIPTION 	"Select bowtie cursor mode"

    ::= { bowtieEntry 6 }


bowtieCursorActive OBJECT-TYPE
    SYNTAX 	INTEGER {
        off(0),
        on(1)
    }
    MAX-ACCESS 	read-write
    STATUS 	current
    DESCRIPTION 	"Enable/Disable bowtie cursors"

    ::= { bowtieEntry 7 }


bowtieCursorH1Pos OBJECT-TYPE
    SYNTAX 	DisplayString
    MAX-ACCESS 	read-write
    STATUS 	current
    DESCRIPTION 	"Position of the first horizontal cursor in bowtie display.The range of values depends on the current video input format and the sweep time base. Time values may be expressed as milliseconds (ms) or microseconds"

    ::= { bowtieEntry 8 }


bowtieCursorH2Pos OBJECT-TYPE
    SYNTAX 	DisplayString
    MAX-ACCESS 	read-write
    STATUS 	current
    DESCRIPTION 	"Position of the second horizontal cursor in bowtie display.The range of values depends on the current video input format and the sweep time base. Time values may be expressed as milliseconds (ms) or microseconds"

    ::= { bowtieEntry 9 }


bowtieCursorV1Pos OBJECT-TYPE
    SYNTAX 	DisplayString
    MAX-ACCESS 	read-write
    STATUS 	current
    DESCRIPTION 	"Position of the first vertical cursor in bowtie display in voltage relative to sweep position"

    ::= { bowtieEntry 10 }


bowtieCursorV2Pos OBJECT-TYPE
    SYNTAX 	DisplayString
    MAX-ACCESS 	read-write
    STATUS 	current
    DESCRIPTION 	"Position of the second vertical cursor in bowtie display in voltage relative to sweep position"

    ::= { bowtieEntry 11 }


bowtieCursorHDelta OBJECT-TYPE
    SYNTAX 	DisplayString
    MAX-ACCESS 	read-only
    STATUS 	current
    DESCRIPTION 	"Time difference between horizontal cursors"

    ::= { bowtieEntry 12 }


bowtieCursorVDelta OBJECT-TYPE
    SYNTAX 	DisplayString
    MAX-ACCESS 	read-only
    STATUS 	current
    DESCRIPTION 	"Time difference between vertical cursors"

    ::= { bowtieEntry 13 }


bowtieHorPos    OBJECT-TYPE
    SYNTAX 	DisplayString
    MAX-ACCESS 	read-write
    STATUS 	current
    DESCRIPTION 	"Bowtie horizontal position as offset from center"

    ::= { bowtieEntry 14 }


bowtieVertPos   OBJECT-TYPE
    SYNTAX 	DisplayString
    MAX-ACCESS 	read-write
    STATUS 	current
    DESCRIPTION 	"Bowtie vertical position in units of mV"

    ::= { bowtieEntry 15 }


bowtieHMag      OBJECT-TYPE
    SYNTAX 	INTEGER {
        off(0),
        on(1),
        gain-x10(10),
        gain-x20(20),
        gain-x25(25),
        gain-x50(50)
    }
    MAX-ACCESS 	read-write
    STATUS 	current
    DESCRIPTION 	"Enable/Disable bowtie horizontal magnification"

    ::= { bowtieEntry 16 }


bowtieCenter    OBJECT-TYPE
    SYNTAX 	INTEGER {
        off(0),
        on(1)
    }
    MAX-ACCESS 	read-write
    STATUS 	current
    DESCRIPTION 	"Center bowtie (write only)"

    ::= { bowtieEntry 17 }


bowtiePercentCurUnits OBJECT-TYPE
    SYNTAX 	INTEGER {
        mv(0),
        percent(1)
    }
    MAX-ACCESS 	read-write
    STATUS 	current
    DESCRIPTION 	"Units of measure for veritcal cursors"

    ::= { bowtieEntry 18 }


bowtieOneOverTCurUnits OBJECT-TYPE
    SYNTAX 	INTEGER {
        sec(0),
        oneOverT(1)
    }
    MAX-ACCESS 	read-write
    STATUS 	current
    DESCRIPTION 	"Units of measure for horizontal cursor delta as time or 1/t."

    ::= { bowtieEntry 19 }


bowtieSetCur100Percent OBJECT-TYPE
    SYNTAX 	INTEGER
    MAX-ACCESS 	read-write
    STATUS 	current
    DESCRIPTION 	"Sets current vertical cursor positions as 0% and 100% reference levels for normal bowtie display (write-only)"

    ::= { bowtieEntry 20 }


bowtieTable     OBJECT-TYPE
    SYNTAX 	SEQUENCE OF BowtieEntry
    MAX-ACCESS 	not-accessible
    STATUS 	current
    DESCRIPTION 	"Table for bowtie display"

    ::= { bowtie 1 }


bowtieEntry     OBJECT-TYPE
    SYNTAX 	BowtieEntry
    MAX-ACCESS 	not-accessible
    STATUS 	current
    DESCRIPTION 	"A row in the Bowtie Table"
    INDEX { currTile }

    ::= { bowtieTable 1 }


BowtieEntry ::= SEQUENCE {
    bowtieMode 	INTEGER,
    bowtieSweepMode 	INTEGER,
    bowtieGain 	INTEGER,
    bowtieVarGainEnable 	INTEGER,
    bowtieVarGain 	DisplayString,
    bowtieCursorMode 	INTEGER,
    bowtieCursorActive 	INTEGER,
    bowtieCursorH1Pos 	DisplayString,
    bowtieCursorH2Pos 	DisplayString,
    bowtieCursorV1Pos 	DisplayString,
    bowtieCursorV2Pos 	DisplayString,
    bowtieCursorHDelta 	DisplayString,
    bowtieCursorVDelta 	DisplayString,
    bowtieHorPos 	DisplayString,
    bowtieVertPos 	DisplayString,
    bowtieHMag 	INTEGER,
    bowtieCenter 	INTEGER,
    bowtiePercentCurUnits 	INTEGER,
    bowtieOneOverTCurUnits 	INTEGER,
    bowtieSetCur100Percent 	INTEGER 
}
-- 
-- Picture Quality Group
-- Picture Quality control and query

blackDuration   OBJECT-TYPE
    SYNTAX 	DisplayString
    MAX-ACCESS 	read-write
    STATUS 	current
    DESCRIPTION 	"Duration of continuous black frames in seconds before a black frame event is declared."

    ::= { pictqual 1 }


frozenFrameDuration OBJECT-TYPE
    SYNTAX 	DisplayString
    MAX-ACCESS 	read-write
    STATUS 	current
    DESCRIPTION 	"Duration of continuous frozen frames in seconds before a frozen frame is declared."

    ::= { pictqual 2 }


blackLevelThreshold OBJECT-TYPE
    SYNTAX 	DisplayString
    MAX-ACCESS 	read-write
    STATUS 	current
    DESCRIPTION 	"Level which is considered black for black frame events (in mv)."

    ::= { pictqual 3 }


frozenFrameLevelThreshold OBJECT-TYPE
    SYNTAX 	DisplayString
    MAX-ACCESS 	read-write
    STATUS 	current
    DESCRIPTION 	"Level which is considered frozen frame."

    ::= { pictqual 4 }


blackAreaWidth  OBJECT-TYPE
    SYNTAX 	INTEGER (1..100)
    MAX-ACCESS 	read-write
    STATUS 	current
    DESCRIPTION 	"Width of the Black measurement area region of interest as percent of the active picture width, range 0% to 100%."

    ::= { pictqual 5 }


blackAreaHeight OBJECT-TYPE
    SYNTAX 	INTEGER (1..100)
    MAX-ACCESS 	read-write
    STATUS 	current
    DESCRIPTION 	"Height of the Black measurement area region of interest as percent of the active picture height, range 0% to 100%."

    ::= { pictqual 6 }


blackAreaHOffset OBJECT-TYPE
    SYNTAX 	INTEGER (-50..50)
    MAX-ACCESS 	read-write
    STATUS 	current
    DESCRIPTION 	"Offset of the Black measurement area region of interest as a percent of the active picture width, range -50% to 50%."

    ::= { pictqual 7 }


blackAreaVOffset OBJECT-TYPE
    SYNTAX 	INTEGER (-50..50)
    MAX-ACCESS 	read-write
    STATUS 	current
    DESCRIPTION 	"Offset of the Black measurement area region of interest as a percent of the active picture height, range -50% to 50%."

    ::= { pictqual 8 }


frozenFrameAreaWidth OBJECT-TYPE
    SYNTAX 	INTEGER (0..100)
    MAX-ACCESS 	read-write
    STATUS 	current
    DESCRIPTION 	"Width of the Frozen Frame measurement area region of interest as percent of the active picture width, range 0% to 100%."

    ::= { pictqual 9 }


frozenFrameAreaHeight OBJECT-TYPE
    SYNTAX 	INTEGER (0..100)
    MAX-ACCESS 	read-write
    STATUS 	current
    DESCRIPTION 	"Height of the Frozen Frame measurement area region of interest as percent of the active picture height, range 0% to 100%."

    ::= { pictqual 10 }


frozenFrameAreaHOffset OBJECT-TYPE
    SYNTAX 	INTEGER (-50..50)
    MAX-ACCESS 	read-write
    STATUS 	current
    DESCRIPTION 	"Offset of the Frozen Frame measurement area region of interest as a percent of the active picture width, range -50% to 50%."

    ::= { pictqual 11 }


frozenFrameAreaVOffset OBJECT-TYPE
    SYNTAX 	INTEGER (-50..50)
    MAX-ACCESS 	read-write
    STATUS 	current
    DESCRIPTION 	"Offset of the Frozen Frame measurement area region of interest as a percent of the active picture height, range -50% to 50%."

    ::= { pictqual 12 }


blackEvents     OBJECT-TYPE
    SYNTAX 	INTEGER
    MAX-ACCESS 	read-only
    STATUS 	current
    DESCRIPTION 	"Black Events Count."

    ::= { pictqual 13 }


frozenEvents    OBJECT-TYPE
    SYNTAX 	INTEGER
    MAX-ACCESS 	read-only
    STATUS 	current
    DESCRIPTION 	"Frozen Events Count."

    ::= { pictqual 14 }


frozenFramePercentThreshold OBJECT-TYPE
    SYNTAX 	INTEGER (1..100)
    MAX-ACCESS 	read-write
    STATUS 	current
    DESCRIPTION 	"Percentage of measurement area that needs to match from one frame to the next to be considered frozen."

    ::= { pictqual 15 }

-- 
-- auxData group
-- Aux Data Status  control variables

auxAncDataTypeIndex OBJECT-TYPE
    SYNTAX 	INTEGER (0..2)
    MAX-ACCESS 	not-accessible
    STATUS 	current
    DESCRIPTION 	"Index For ANC Data Type for  Aux Anc Data  Table."

    ::= { auxData 1 }


auxAncDataName  OBJECT-TYPE
    SYNTAX 	DisplayString
    MAX-ACCESS 	read-write
    STATUS 	current
    DESCRIPTION 	"ANC Data Type Name which is displayed in Aux Data Status Page"

    ::= { auxAncDataEntry 1 }


auxAncDataDID   OBJECT-TYPE
    SYNTAX 	INTEGER (1..255)
    MAX-ACCESS 	read-write
    STATUS 	current
    DESCRIPTION 	"anc data ID (DID) displayed in Aux Data Status Page."

    ::= { auxAncDataEntry 2 }


auxAncDataSDID  OBJECT-TYPE
    SYNTAX 	INTEGER (0..255)
    MAX-ACCESS 	read-write
    STATUS 	current
    DESCRIPTION 	"anc secondary data ID (SDID) displayed in Aux Data Status Page."

    ::= { auxAncDataEntry 3 }


auxAncDataTable OBJECT-TYPE
    SYNTAX 	SEQUENCE OF AuxAncDataEntry
    MAX-ACCESS 	not-accessible
    STATUS 	current
    DESCRIPTION 	"Table for Anc Data types in Aux Data Status Page"

    ::= { auxData 2 }


auxAncDataEntry OBJECT-TYPE
    SYNTAX 	AuxAncDataEntry
    MAX-ACCESS 	not-accessible
    STATUS 	current
    DESCRIPTION 	"A row in the auxAncDataTable table "
    INDEX { auxAncDataTypeIndex }

    ::= { auxAncDataTable 1 }


AuxAncDataEntry ::= SEQUENCE {
    auxAncDataName 	DisplayString,
    auxAncDataDID 	INTEGER,
    auxAncDataSDID 	INTEGER 
}

resetAuxAncData OBJECT-TYPE
    SYNTAX 	INTEGER {
        ready(0),
        reset(1)
    }
    MAX-ACCESS 	read-write
    STATUS 	current
    DESCRIPTION 	"Reset the ANC Data in Aux Data Status page (write only)."

    ::= { auxData 3 }


sourceId        OBJECT-TYPE
    SYNTAX 	DisplayString
    MAX-ACCESS 	read-only
    STATUS 	current
    DESCRIPTION 	"Source ID text on selected input"

    ::= { sourceIdEntry 1 }


sourceIdPresent OBJECT-TYPE
    SYNTAX 	INTEGER {
        missing(0),
        present(1)
    }
    MAX-ACCESS 	read-only
    STATUS 	current
    DESCRIPTION 	"Presence of Source ID on selected input"

    ::= { sourceIdEntry 2 }


sourceIdError   OBJECT-TYPE
    SYNTAX 	INTEGER {
        ok(0),
        errors(1)
    }
    MAX-ACCESS 	read-only
    STATUS 	current
    DESCRIPTION 	"Errors on Source ID on selected input"

    ::= { sourceIdEntry 3 }


sourceIdTable   OBJECT-TYPE
    SYNTAX 	SEQUENCE OF SourceIdEntry
    MAX-ACCESS 	not-accessible
    STATUS 	current
    DESCRIPTION 	"Table for Source ID"

    ::= { auxData 4 }


sourceIdEntry   OBJECT-TYPE
    SYNTAX 	SourceIdEntry
    MAX-ACCESS 	not-accessible
    STATUS 	current
    DESCRIPTION 	"A row in the sourceIdTable table "
    INDEX { currChan }

    ::= { sourceIdTable 1 }


SourceIdEntry ::= SEQUENCE {
    sourceId 	DisplayString,
    sourceIdPresent 	INTEGER,
    sourceIdError 	INTEGER 
}
-- 
-- Audio Loudness Group
-- Audio Loudness control and query

lkfsGraphScale  OBJECT-TYPE
    SYNTAX 	INTEGER {
        trend90sec(0),
        trend180sec(1),
        bar7pt5min(2),
        bar15min(3),
        bar30min(4),
        bar90min(5),
        bar3hr(6),
        bar7pt5hr(7),
        bar15hr(8),
        bar30hr(9)
    }
    MAX-ACCESS 	read-write
    STATUS 	current
    DESCRIPTION 	"Audio Loudness Graph Horizontal  Scale Settings"

    ::= { audioLoudness 1 }


lkfsGraphGain   OBJECT-TYPE
    SYNTAX 	INTEGER {
        full0to60(0),
        eightToForty(1),
        twelveToThirtysix(2)
    }
    MAX-ACCESS 	read-write
    STATUS 	current
    DESCRIPTION 	"Audio Loudess Graph Vertical Scale Settings"

    ::= { audioLoudness 2 }


lkfsSessionReset OBJECT-TYPE
    SYNTAX 	INTEGER {
        reset(0)
    }
    MAX-ACCESS 	read-write
    STATUS 	current
    DESCRIPTION 	"Audio Loudness Session Reset"

    ::= { audioLoudness 3 }


lkfsValueShort  OBJECT-TYPE
    SYNTAX 	AudioLevel
    MAX-ACCESS 	read-only
    STATUS 	current
    DESCRIPTION 	"Read Value LKFS Short from Loudness Session."

    ::= { audioLoudness 4 }


lkfsValueInf    OBJECT-TYPE
    SYNTAX 	AudioLevel
    MAX-ACCESS 	read-only
    STATUS 	current
    DESCRIPTION 	"Read Value LKFS inf from Loudness Session."

    ::= { audioLoudness 5 }


lkfsValuePeak   OBJECT-TYPE
    SYNTAX 	AudioLevel
    MAX-ACCESS 	read-only
    STATUS 	current
    DESCRIPTION 	"Read Value True Peak from Loudness Session."

    ::= { audioLoudness 6 }


loudSessDialNorm OBJECT-TYPE
    SYNTAX 	AudioLevel
    MAX-ACCESS 	read-only
    STATUS 	current
    DESCRIPTION 	"Read Value Dialnorm from Loudness Session."

    ::= { audioLoudness 7 }


lkfsSessionRuntime OBJECT-TYPE
    SYNTAX 	DisplayString
    MAX-ACCESS 	read-only
    STATUS 	current
    DESCRIPTION 	"."

    ::= { audioLoudness 8 }


loudnessRange   OBJECT-TYPE
    SYNTAX 	AudioLevel
    MAX-ACCESS 	read-only
    STATUS 	current
    DESCRIPTION 	"Read Value Loudness Range."

    ::= { audioLoudness 9 }


loudnessClipSession OBJECT-TYPE
    SYNTAX 	INTEGER {
        reset(0),
        pause(1),
        resume(2),
        save(3),
        clearAll(4)
    }
    MAX-ACCESS 	read-write
    STATUS 	current
    DESCRIPTION 	"Loudness Clip Session Control."

    ::= { loudEventEntry 1 }


loudnessClipType OBJECT-TYPE
    SYNTAX 	INTEGER {
        unknown(0),
        advertisement(1),
        program(2)
    }
    MAX-ACCESS 	read-write
    STATUS 	current
    DESCRIPTION 	"Loudness Event Session Type for the Current Audio Clip. This may be Unknown, Advertisement, or Program."

    ::= { loudEventEntry 2 }


loudEventTable  OBJECT-TYPE
    SYNTAX 	SEQUENCE OF LoudEventEntry
    MAX-ACCESS 	not-accessible
    STATUS 	current
    DESCRIPTION 	"Table for Loud Event Control"

    ::= { audioLoudness 10 }


loudEventEntry  OBJECT-TYPE
    SYNTAX 	LoudEventEntry
    MAX-ACCESS 	not-accessible
    STATUS 	current
    DESCRIPTION 	"A row in the Loudness Event table "
    INDEX { currChan }

    ::= { loudEventTable 1 }


LoudEventEntry ::= SEQUENCE {
    loudnessClipSession 	INTEGER,
    loudnessClipType 	INTEGER 
}

loudnessStandard OBJECT-TYPE
    SYNTAX 	DisplayString
    MAX-ACCESS 	read-only
    STATUS 	current
    DESCRIPTION 	"Read value of Loudness Standard from Loudness Session."

    ::= { audioLoudness 11 }


loudSessTCJogShuttle OBJECT-TYPE
    SYNTAX 	INTEGER {
        ignore(0),
        pause(1),
        newClip(2)
    }
    MAX-ACCESS 	read-write
    STATUS 	current
    DESCRIPTION 	"Audio session/trigger log behaviour on timecode jog/shuttle."

    ::= { audioLoudness 12 }


loudSessTCStopPause OBJECT-TYPE
    SYNTAX 	INTEGER {
        ignore(0),
        pause(1),
        newClip(2)
    }
    MAX-ACCESS 	read-write
    STATUS 	current
    DESCRIPTION 	"Audio session/trigger log behaviour on timecode stop or pause."

    ::= { audioLoudness 13 }


loudSessTCLossUnlock OBJECT-TYPE
    SYNTAX 	INTEGER {
        ignore(0),
        pause(1),
        newClip(2)
    }
    MAX-ACCESS 	read-write
    STATUS 	current
    DESCRIPTION 	"Audio session/trigger log behaviour loss of timecode."

    ::= { audioLoudness 14 }


loudSessTCJumpChange OBJECT-TYPE
    SYNTAX 	INTEGER {
        ignore(0),
        newClip(1)
    }
    MAX-ACCESS 	read-write
    STATUS 	current
    DESCRIPTION 	"Audio session/trigger log behaviour on timecode discontinuity or source change."

    ::= { audioLoudness 15 }


loudSessTCInAction OBJECT-TYPE
    SYNTAX 	INTEGER {
        ignore(0),
        newClip(1)
    }
    MAX-ACCESS 	read-write
    STATUS 	current
    DESCRIPTION 	"Audio session/trigger log behaviour when timecode IN value is reached."

    ::= { audioLoudness 16 }


loudSessTCInTime OBJECT-TYPE
    SYNTAX 	DisplayString
    MAX-ACCESS 	read-only
    STATUS 	current
    DESCRIPTION 	"IN (start) timecode value of session control."

    ::= { audioLoudness 17 }


loudSessTCOutAction OBJECT-TYPE
    SYNTAX 	INTEGER {
        ignore(0),
        endClip(1)
    }
    MAX-ACCESS 	read-write
    STATUS 	current
    DESCRIPTION 	"Audio session/trigger log behaviour when timecode OUT value is reached."

    ::= { audioLoudness 18 }


loudSessTCOutTime OBJECT-TYPE
    SYNTAX 	DisplayString
    MAX-ACCESS 	read-only
    STATUS 	current
    DESCRIPTION 	"OUT (end) timecode value of session control."

    ::= { audioLoudness 19 }

-- 
-- extref group
-- External Reference Waveform mode variables

extrefHorPos    OBJECT-TYPE
    SYNTAX 	DisplayString
    MAX-ACCESS 	read-write
    STATUS 	current
    DESCRIPTION 	"External reference waveform horizontal position. Relative Offset Range -1.0 to +1.0."

    ::= { extrefEntry 1 }


extrefVertPos   OBJECT-TYPE
    SYNTAX 	DisplayString
    MAX-ACCESS 	read-write
    STATUS 	current
    DESCRIPTION 	"Waveform vertical position in units of mV"

    ::= { extrefEntry 2 }


extrefCenter    OBJECT-TYPE
    SYNTAX 	INTEGER {
        off(0),
        on(1)
    }
    MAX-ACCESS 	read-write
    STATUS 	current
    DESCRIPTION 	"Center EXTREFexternal reference waveform (write only)"

    ::= { extrefEntry 3 }


extrefGain      OBJECT-TYPE
    SYNTAX 	INTEGER {
        gain-x1(1),
        gain-x2(2),
        gain-x5(5)
    }
    MAX-ACCESS 	read-write
    STATUS 	current
    DESCRIPTION 	"External reference waveform fixed gain"

    ::= { extrefEntry 4 }


extrefVarGainEnable OBJECT-TYPE
    SYNTAX 	INTEGER {
        off(0),
        on(1)
    }
    MAX-ACCESS 	read-write
    STATUS 	current
    DESCRIPTION 	"Enable/disable external reference waveform variable gain"

    ::= { extrefEntry 5 }


extrefVarGain   OBJECT-TYPE
    SYNTAX 	DisplayString
    MAX-ACCESS 	read-write
    STATUS 	current
    DESCRIPTION 	"External reference variable gain value (effective).  Range of values depend on current value of extrefGain."

    ::= { extrefEntry 6 }


extrefTable     OBJECT-TYPE
    SYNTAX 	SEQUENCE OF ExtrefEntry
    MAX-ACCESS 	not-accessible
    STATUS 	current
    DESCRIPTION 	"Table for EXTREF display mode"

    ::= { extref 1 }


extrefEntry     OBJECT-TYPE
    SYNTAX 	ExtrefEntry
    MAX-ACCESS 	not-accessible
    STATUS 	current
    DESCRIPTION 	"A row in the extref table "
    INDEX { currTile }

    ::= { extrefTable 1 }


ExtrefEntry ::= SEQUENCE {
    extrefHorPos 	DisplayString,
    extrefVertPos 	DisplayString,
    extrefCenter 	INTEGER,
    extrefGain 	INTEGER,
    extrefVarGainEnable 	INTEGER,
    extrefVarGain 	DisplayString 
}
-- 
-- generator group
-- generator output variables

outputGenSdiPattern OBJECT-TYPE
    SYNTAX 	INTEGER {
        color-bar-100(0),
        color-bar-75(1),
        pathological-signal(2)
    }
    MAX-ACCESS 	read-write
    STATUS 	current
    DESCRIPTION 	"Signal generator output pattern."

    ::= { generator 1 }


outputGenSdiFormat OBJECT-TYPE
    SYNTAX 	INTEGER {
        std-525i-59-94(0),
        std-625i-50(1),
        std-1080i-50(2),
        std-1080i-59-94(3),
        std-1080i-60(4),
        std-1080p-50(5),
        std-1080p-59-94(6),
        std-1080p-60(7),
        std-720p-50(8),
        std-720p-5994(9),
        std-720p-60(10),
        std-1080p-23-98(11),
        std-1080p-24(12),
        std-1080p-25(13),
        std-1080p-2997(14),
        std-1080p-30(15),
        std-1080sF-2398(16),
        std-1080sF-24(17)
    }
    MAX-ACCESS 	read-write
    STATUS 	current
    DESCRIPTION 	"Signal generator output format."

    ::= { generator 2 }


outputGenSdiLevel OBJECT-TYPE
    SYNTAX 	INTEGER {
        level-A(0),
        level-B(1)
    }
    MAX-ACCESS 	read-write
    STATUS 	current
    DESCRIPTION 	"Signal generator 3G output level."

    ::= { generator 3 }


outputSdiSource OBJECT-TYPE
    SYNTAX 	INTEGER {
        pixmon(0),
        loopout-follows-input(1),
        test-signal(2)
    }
    MAX-ACCESS 	read-write
    STATUS 	current
    DESCRIPTION 	"Signal generator output source (Loopout Follows Input or Test Signal)."

    ::= { generator 4 }


outputAesSource OBJECT-TYPE
    SYNTAX 	INTEGER {
        off(0),
        test-signal(1),
        aes-loopout(2),
        audio-output(3)
    }
    MAX-ACCESS 	read-write
    STATUS 	current
    DESCRIPTION 	"AES output source"

    ::= { generator 5 }


channel         OBJECT-TYPE
    SYNTAX 	INTEGER (0..1)
    MAX-ACCESS 	not-accessible
    STATUS 	current
    DESCRIPTION 	"output channel number for AES output table."

    ::= { generator 6 }


outputGenAesFreq OBJECT-TYPE
    SYNTAX 	INTEGER {
        mute(0),
        freq-100Hz(1),
        freq-200Hz(2),
        freq-400Hz(3),
        freq-800Hz(4),
        freq-1KHz(5),
        freq-2KHz(6),
        freq-4KHz(7),
        freq-10KHz(8),
        freq-18KHz(9)
    }
    MAX-ACCESS 	read-write
    STATUS 	current
    DESCRIPTION 	"Signal generator AES audio frequency "

    ::= { outputGenAesEntry 1 }


outputGenAesAmp OBJECT-TYPE
    SYNTAX 	AudioLevel (-60..0)
    MAX-ACCESS 	read-write
    STATUS 	current
    DESCRIPTION 	"Signal generator AES audio amplitude "

    ::= { outputGenAesEntry 2 }


outputGenAesTable OBJECT-TYPE
    SYNTAX 	SEQUENCE OF OutputGenAesEntry
    MAX-ACCESS 	not-accessible
    STATUS 	current
    DESCRIPTION 	"Table of aes output statistics for each audio channel that isassociated with AES output"

    ::= { generator 7 }


outputGenAesEntry OBJECT-TYPE
    SYNTAX 	OutputGenAesEntry
    MAX-ACCESS 	not-accessible
    STATUS 	current
    DESCRIPTION 	"A row in the output table "
    INDEX { channel }

    ::= { outputGenAesTable 1 }


OutputGenAesEntry ::= SEQUENCE {
    outputGenAesFreq 	INTEGER,
    outputGenAesAmp 	AudioLevel 
}

outputGenAesBitDepth OBJECT-TYPE
    SYNTAX 	INTEGER {
        depth-20bit(0),
        depth-24bit(1)
    }
    MAX-ACCESS 	read-write
    STATUS 	current
    DESCRIPTION 	"Signal generator audio bit depth "

    ::= { generator 8 }


group           OBJECT-TYPE
    SYNTAX 	INTEGER (0..3)
    MAX-ACCESS 	not-accessible
    STATUS 	current
    DESCRIPTION 	"embedded audio group number for AES output table."

    ::= { generator 9 }


outputGenEmbAudGroup OBJECT-TYPE
    SYNTAX 	INTEGER {
        off(0),
        on(1)
    }
    MAX-ACCESS 	read-write
    STATUS 	current
    DESCRIPTION 	"Embedded audio group off or on status"

    ::= { outputGenEmbAudioEntry 1 }


outputGenEmbAudioTable OBJECT-TYPE
    SYNTAX 	SEQUENCE OF OutputGenEmbAudioEntry
    MAX-ACCESS 	not-accessible
    STATUS 	current
    DESCRIPTION 	"Table of embedded audio off or on status for each audio group"

    ::= { generator 10 }


outputGenEmbAudioEntry OBJECT-TYPE
    SYNTAX 	OutputGenEmbAudioEntry
    MAX-ACCESS 	not-accessible
    STATUS 	current
    DESCRIPTION 	"A row in the output generator embedded audio table "
    INDEX { group }

    ::= { outputGenEmbAudioTable 1 }


OutputGenEmbAudioEntry ::= SEQUENCE {
    outputGenEmbAudGroup 	INTEGER 
}

movingPictEnable OBJECT-TYPE
    SYNTAX 	INTEGER {
        off(0),
        on(1)
    }
    MAX-ACCESS 	read-write
    STATUS 	current
    DESCRIPTION 	"Moving picture Enable or Disable "

    ::= { generator 11 }


movingPictFrames OBJECT-TYPE
    SYNTAX 	INTEGER (0..16)
    MAX-ACCESS 	read-write
    STATUS 	current
    DESCRIPTION 	"Test signal moving picture frames "

    ::= { generator 12 }


movingPictSamples OBJECT-TYPE
    SYNTAX 	INTEGER (-15..15)
    MAX-ACCESS 	read-write
    STATUS 	current
    DESCRIPTION 	"Test signal moving picture samples "

    ::= { generator 13 }


movingCircleMode OBJECT-TYPE
    SYNTAX 	INTEGER {
        off(0),
        horizontal(1),
        vertical(2),
        random(3)
    }
    MAX-ACCESS 	read-write
    STATUS 	current
    DESCRIPTION 	"Test signal moving circle mode "

    ::= { generator 14 }


genlockEnable   OBJECT-TYPE
    SYNTAX 	INTEGER {
        disable(0),
        enable(1)
    }
    MAX-ACCESS 	read-write
    STATUS 	current
    DESCRIPTION 	"Video output control for Genlock Enable or Disable "

    ::= { generator 15 }


genlockOffsetV  OBJECT-TYPE
    SYNTAX 	INTEGER (-562..562)
    MAX-ACCESS 	read-write
    STATUS 	current
    DESCRIPTION 	"Video Out Signal timing Vertical offset in lines "

    ::= { generator 16 }


genlockOffsetH  OBJECT-TYPE
    SYNTAX 	DisplayString
    MAX-ACCESS 	read-write
    STATUS 	current
    DESCRIPTION 	"Video Out Signal timing Horizontal offset in time  "

    ::= { generator 17 }


sdiStressAmplitude OBJECT-TYPE
    SYNTAX 	INTEGER (0..300)
    MAX-ACCESS 	read-write
    STATUS 	current
    DESCRIPTION 	"SDI Stress Loop Amplitude"

    ::= { generator 18 }

-- 
-- sfp group
-- sfp Waveform mode variables

currSfpMod      OBJECT-TYPE
    SYNTAX 	INTEGER {
        module1(0)
    }
    MAX-ACCESS 	not-accessible
    STATUS 	current
    DESCRIPTION 	"Currently Selected Module. This is used as index in tables"

    ::= { sfp 1 }


sfpModuleStatus OBJECT-TYPE
    SYNTAX 	INTEGER {
        unknown(0),
        notInstalled(1),
        notRecognised(2),
        msa(3),
        nonMsa(4)
    }
    MAX-ACCESS 	read-only
    STATUS 	current
    DESCRIPTION 	"SFP Module Status None, dummyStatus "

    ::= { sfpEntry 1 }


sfpModuleType   OBJECT-TYPE
    SYNTAX 	INTEGER {
        none(0),
        soleTransmitter(1),
        soleReceiver(2),
        transceiver(3),
        dualTransmitter(4),
        dualReceiver(5)
    }
    MAX-ACCESS 	read-write
    STATUS 	current
    DESCRIPTION 	"SFP Module type None, Sole transmitter, Sole Receiver, Transceiver, Dual transmitters, Dual Reciivers "

    ::= { sfpEntry 2 }


sfpModuleId     OBJECT-TYPE
    SYNTAX 	DisplayString
    MAX-ACCESS 	read-only
    STATUS 	current
    DESCRIPTION 	"SFP Module ID ,Unknown, GBIC, Soldered, SFP transceiver "

    ::= { sfpEntry 3 }


sfpExtId        OBJECT-TYPE
    SYNTAX 	DisplayString
    MAX-ACCESS 	read-only
    STATUS 	current
    DESCRIPTION 	"SfP Extension ID ,SFP , Unknown"

    ::= { sfpEntry 4 }


sfpConnType     OBJECT-TYPE
    SYNTAX 	DisplayString
    MAX-ACCESS 	read-only
    STATUS 	current
    DESCRIPTION 	"SFP Connection type, Unknown, SC, FC Style 1/2 copper, BNC/TNC, FC Coaxial Headers, Fiber Jack, LC, MT-RJ, MU, SG, Optical pigtail, MU, HSSDC IT, Copper pigtail"

    ::= { sfpEntry 5 }


sfpXcvrCode     OBJECT-TYPE
    SYNTAX 	DisplayString
    MAX-ACCESS 	read-only
    STATUS 	current
    DESCRIPTION 	"Tranceiver code description"

    ::= { sfpEntry 6 }


sfpEncoding     OBJECT-TYPE
    SYNTAX 	DisplayString
    MAX-ACCESS 	read-only
    STATUS 	current
    DESCRIPTION 	"Unspecified, 8B10B, 4B5B, NRZ, Manchester"

    ::= { sfpEntry 7 }


sfpNominalBitrate OBJECT-TYPE
    SYNTAX 	DisplayString
    MAX-ACCESS 	read-only
    STATUS 	current
    DESCRIPTION 	"Nominal bitrate"

    ::= { sfpEntry 8 }


sfpReserved13   OBJECT-TYPE
    SYNTAX 	DisplayString
    MAX-ACCESS 	read-only
    STATUS 	current
    DESCRIPTION 	"SFP Reserved 13 value "

    ::= { sfpEntry 9 }


sfpLength9Micron OBJECT-TYPE
    SYNTAX 	DisplayString
    MAX-ACCESS 	read-only
    STATUS 	current
    DESCRIPTION 	" SFP length 9 Micron"

    ::= { sfpEntry 10 }


sfpLength50Micron OBJECT-TYPE
    SYNTAX 	DisplayString
    MAX-ACCESS 	read-only
    STATUS 	current
    DESCRIPTION 	" SFP Length 50 Micron"

    ::= { sfpEntry 11 }


sfpLength62Micron OBJECT-TYPE
    SYNTAX 	DisplayString
    MAX-ACCESS 	read-only
    STATUS 	current
    DESCRIPTION 	" SFP Length 62 Micron"

    ::= { sfpEntry 12 }


sfpLengthCopper OBJECT-TYPE
    SYNTAX 	DisplayString
    MAX-ACCESS 	read-only
    STATUS 	current
    DESCRIPTION 	" SFP length Copper"

    ::= { sfpEntry 13 }


sfpReserved19   OBJECT-TYPE
    SYNTAX 	DisplayString
    MAX-ACCESS 	read-only
    STATUS 	current
    DESCRIPTION 	"SFP Reserved 19 "

    ::= { sfpEntry 14 }


sfpVendorName   OBJECT-TYPE
    SYNTAX 	DisplayString
    MAX-ACCESS 	read-only
    STATUS 	current
    DESCRIPTION 	"SFP VENDOR NAME description"

    ::= { sfpEntry 15 }


sfpReserved36   OBJECT-TYPE
    SYNTAX 	DisplayString
    MAX-ACCESS 	read-only
    STATUS 	current
    DESCRIPTION 	"SFP Reserved 36"

    ::= { sfpEntry 16 }


sfpVendorOui    OBJECT-TYPE
    SYNTAX 	DisplayString
    MAX-ACCESS 	read-only
    STATUS 	current
    DESCRIPTION 	" SFP Module Vendor Oui description"

    ::= { sfpEntry 17 }


sfpVendorPN     OBJECT-TYPE
    SYNTAX 	DisplayString
    MAX-ACCESS 	read-only
    STATUS 	current
    DESCRIPTION 	"SFP Module Vendor PN "

    ::= { sfpEntry 18 }


sfpReserved5658 OBJECT-TYPE
    SYNTAX 	DisplayString
    MAX-ACCESS 	read-only
    STATUS 	current
    DESCRIPTION 	"SFP Module Reserved 5658"

    ::= { sfpEntry 19 }


sfpVendorRev    OBJECT-TYPE
    SYNTAX 	DisplayString
    MAX-ACCESS 	read-only
    STATUS 	current
    DESCRIPTION 	" SFP Module Vendor REV"

    ::= { sfpEntry 20 }


sfpWavelength   OBJECT-TYPE
    SYNTAX 	DisplayString
    MAX-ACCESS 	read-only
    STATUS 	current
    DESCRIPTION 	"SFP Module Wavelength"

    ::= { sfpEntry 21 }


sfpReserved62   OBJECT-TYPE
    SYNTAX 	DisplayString
    MAX-ACCESS 	read-only
    STATUS 	current
    DESCRIPTION 	"SFP Reserved 62"

    ::= { sfpEntry 22 }


sfpCCBase       OBJECT-TYPE
    SYNTAX 	DisplayString
    MAX-ACCESS 	read-only
    STATUS 	current
    DESCRIPTION 	"SFP CC base "

    ::= { sfpEntry 23 }


sfpOptions      OBJECT-TYPE
    SYNTAX 	DisplayString
    MAX-ACCESS 	read-only
    STATUS 	current
    DESCRIPTION 	" SFP OPTIONS"

    ::= { sfpEntry 24 }


sfpUpperBitrateMargin OBJECT-TYPE
    SYNTAX 	DisplayString
    MAX-ACCESS 	read-only
    STATUS 	current
    DESCRIPTION 	"SFP Upper Bitrate Margin"

    ::= { sfpEntry 25 }


sfpLowerBitrateMargin OBJECT-TYPE
    SYNTAX 	DisplayString
    MAX-ACCESS 	read-only
    STATUS 	current
    DESCRIPTION 	"SFP Lower Bitrate Margin"

    ::= { sfpEntry 26 }


sfpVendorSN     OBJECT-TYPE
    SYNTAX 	DisplayString
    MAX-ACCESS 	read-only
    STATUS 	current
    DESCRIPTION 	" SFP Vendor SN Description"

    ::= { sfpEntry 27 }


sfpMfgDateCode  OBJECT-TYPE
    SYNTAX 	DisplayString
    MAX-ACCESS 	read-only
    STATUS 	current
    DESCRIPTION 	" SFP Manufacture Date Code"

    ::= { sfpEntry 28 }


sfpReserved9294 OBJECT-TYPE
    SYNTAX 	DisplayString
    MAX-ACCESS 	read-only
    STATUS 	current
    DESCRIPTION 	"SFP Reserved 9294"

    ::= { sfpEntry 29 }


sfpCCExt        OBJECT-TYPE
    SYNTAX 	DisplayString
    MAX-ACCESS 	read-only
    STATUS 	current
    DESCRIPTION 	"SFP CC Extension"

    ::= { sfpEntry 30 }


sfpTable        OBJECT-TYPE
    SYNTAX 	SEQUENCE OF SfpEntry
    MAX-ACCESS 	not-accessible
    STATUS 	current
    DESCRIPTION 	"Table for sfp"

    ::= { sfp 2 }


sfpEntry        OBJECT-TYPE
    SYNTAX 	SfpEntry
    MAX-ACCESS 	not-accessible
    STATUS 	current
    DESCRIPTION 	"a row in the sfp table"
    INDEX { currSfpMod }

    ::= { sfpTable 1 }


SfpEntry ::= SEQUENCE {
    sfpModuleStatus 	INTEGER,
    sfpModuleType 	INTEGER,
    sfpModuleId 	DisplayString,
    sfpExtId 	DisplayString,
    sfpConnType 	DisplayString,
    sfpXcvrCode 	DisplayString,
    sfpEncoding 	DisplayString,
    sfpNominalBitrate 	DisplayString,
    sfpReserved13 	DisplayString,
    sfpLength9Micron 	DisplayString,
    sfpLength50Micron 	DisplayString,
    sfpLength62Micron 	DisplayString,
    sfpLengthCopper 	DisplayString,
    sfpReserved19 	DisplayString,
    sfpVendorName 	DisplayString,
    sfpReserved36 	DisplayString,
    sfpVendorOui 	DisplayString,
    sfpVendorPN 	DisplayString,
    sfpReserved5658 	DisplayString,
    sfpVendorRev 	DisplayString,
    sfpWavelength 	DisplayString,
    sfpReserved62 	DisplayString,
    sfpCCBase 	DisplayString,
    sfpOptions 	DisplayString,
    sfpUpperBitrateMargin 	DisplayString,
    sfpLowerBitrateMargin 	DisplayString,
    sfpVendorSN 	DisplayString,
    sfpMfgDateCode 	DisplayString,
    sfpReserved9294 	DisplayString,
    sfpCCExt 	DisplayString 
}

END
